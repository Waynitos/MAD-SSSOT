'' =====================================================================
'' SUPER_CLEAN_SWEEPER.iLogicVb
'' Copy Design with full provenance architecture
'' Version: 1.0.0 — 2026-11-04
''
'' PURPOSE
''   Replicates Vault Copy Design outside of Vault.
''   Copies an entire GA assembly tree to a new folder with a new
''   project prefix, using SaveAs (not File.Copy) so every new file
''   gets a fresh internal GUID.  Provenance iProperties are written
''   to every new model file at save time (zero extra open/save cost
''   since the file is already in Inventor's session).
''
'' KEY ARCHITECTURAL DIFFERENCES FROM TRAVERSE RULE (Mode 6)
''   1. SaveAs replaces File.Copy — fresh GUID on every new file,
''      matching Vault Copy Design behaviour.
''   2. WriteProvenanceProps writes to every new .iam / .ipt:
''         CS_SourcePath    = original full path before copy
''         CS_SourceName    = original filename
''         CS_CopyProject   = new project prefix (e.g. PJ00222)
''         CS_CopyDate      = copy date (yyyy-MM-dd)
''         CS_SourceGUID    = original InternalName GUID
''   3. CS_SourceGUID is captured BEFORE the SaveAs call because
''      Inventor assigns a new GUID to the saved file; the original
''      GUID is then written to the new file as CS_SourceGUID.
''   4. CS_ModelRefs is written to every new .idw / .dwg:
''      pipe-delimited list of old model paths the drawing referenced.
''      Enables autonomous drawing relink — scan _CLEAN for files
''      whose CS_SourcePath matches, then ReplaceReference.
''   5. Provenance skip guard: if a destination file already carries
''      CS_CopyProject = new prefix, it was processed in a prior run;
''      skip it rather than overwriting.
''
'' CODE-ASSASSIN FIXES (2026-11-04 audit)
''   F1. Sub Main: Try/Finally restores SilentOperation — prevents
''       Inventor being left dialog-less if an unexpected exception
''       escapes the per-file Try/Catch during Phase 2 or 3.
''   F2. Phase 3: oDoc3.File null-checked before .ReferencedFileDescriptors
''       to produce a clear P3-FILE-NULL log entry instead of a
''       misleading P3-ERROR on certain unresolved document types.
''   F3. WalkTree: Content Centre parts excluded before they enter the
''       rename map (kCCPartDocumentSubType check + path heuristic).
''   F4. Mid-loop sLog concatenation removed — sLog was accumulating
''       all per-file detail but only used for the final MessageBox
''       (which truncates at ~32 KB anyway).  Counters already build
''       the correct sSummary at step 9.
''
'' PHASES
''   Phase 1  Build old->new rename map  (walk GA tree, no disk writes)
''   Phase 2  SaveAs + Provenance        (creates new files, writes props)
''   Phase 3  Fix internal references    (open new .iam/.ipt, rewrite FDs)
''   (Phase 4 / drawing relink is a separate follow-on step)
''
'' ILOGIC COMPILER CONSTRAINTS (from ILOGIC_EDIT_PROTOCOL.md)
''   - No System.Drawing.Color / SystemColors
''   - For Each loop variables: As Object for all non-primitive types
''   - ReferencedDocumentDescriptors (not ReferencedDocuments) for DART SHUT
''   - Strip "<" state tag from descriptor paths
''   - No Imports System.IO or Imports System.Windows.Forms (pre-imported)
''   - No module-level Dim declarations (outside Sub/Function)
''   - Sub Main() is mandatory; helpers defined ABOVE their callers
'' =====================================================================


' ─────────────────────────────────────────────────────────────────────────────
' HELPER: Write provenance iProperties to a document
' Call AFTER the document has been SaveAs'd to its new path and is open.
' aNames / aVals are parallel arrays; we try to set each property,
' adding it if it does not already exist.
' ─────────────────────────────────────────────────────────────────────────────
Sub WriteProvenanceProps(oDoc As Document, sOldPath As String, _
                          sNewProject As String, sOldGUID As String, _
                          sLogPath As String)
    Try
        Dim oUDP As PropertySet = oDoc.PropertySets("Inventor User Defined Properties")
        Dim aNames(4) As String
        Dim aVals(4) As String
        aNames(0) = "CS_SourcePath"    : aVals(0) = sOldPath
        aNames(1) = "CS_SourceName"    : aVals(1) = System.IO.Path.GetFileName(sOldPath)
        aNames(2) = "CS_CopyProject"   : aVals(2) = sNewProject
        aNames(3) = "CS_CopyDate"      : aVals(3) = Now.ToString("yyyy-MM-dd")
        aNames(4) = "CS_SourceGUID"    : aVals(4) = sOldGUID
        Dim i As Integer
        For i = 0 To 4
            Dim sPropName As String = aNames(i)
            Dim sPropVal  As String = aVals(i)
            Try
                oUDP.Item(sPropName).Value = sPropVal
            Catch
                Try
                    oUDP.Add(sPropVal, sPropName)
                Catch exAdd As Exception
                    Try
                        System.IO.File.AppendAllText(sLogPath, _
                            "PROV-WARN: could not set " & sPropName & _
                            " on " & oDoc.DisplayName & " — " & exAdd.Message & vbCrLf)
                    Catch : End Try
                End Try
            End Try
        Next i
    Catch ex As Exception
        Try
            System.IO.File.AppendAllText(sLogPath, _
                "PROV-FAIL: " & oDoc.DisplayName & " — " & ex.Message & vbCrLf)
        Catch : End Try
    End Try
End Sub


' ─────────────────────────────────────────────────────────────────────────────
' HELPER: Write CS_ModelRefs to a drawing document
' Writes pipe-delimited list of old model paths the drawing referenced.
' This enables autonomous relink: scan _CLEAN for CS_SourcePath matches.
' ─────────────────────────────────────────────────────────────────────────────
Sub WriteDrawingModelRefs(oDwg As Document, _
                           oModelPaths As System.Collections.Generic.List(Of String), _
                           sLogPath As String)
    If oModelPaths Is Nothing Then Return
    If oModelPaths.Count = 0 Then Return
    Dim sJoined As String = String.Join("|", oModelPaths.ToArray())
    Try
        Dim oUDP As PropertySet = oDwg.PropertySets("Inventor User Defined Properties")
        Try
            oUDP.Item("CS_ModelRefs").Value = sJoined
        Catch
            Try
                oUDP.Add(sJoined, "CS_ModelRefs")
            Catch exA As Exception
                Try
                    System.IO.File.AppendAllText(sLogPath, _
                        "MODELREFS-WARN: " & oDwg.DisplayName & " — " & exA.Message & vbCrLf)
                Catch : End Try
            End Try
        End Try
    Catch ex As Exception
        Try
            System.IO.File.AppendAllText(sLogPath, _
                "MODELREFS-FAIL: " & oDwg.DisplayName & " — " & ex.Message & vbCrLf)
        Catch : End Try
    End Try
End Sub


' ─────────────────────────────────────────────────────────────────────────────
' HELPER: Check if destination file was already processed in a prior run
' Returns True only when the destination exists AND carries
' CS_CopyProject = sProject (checked via already-open doc if possible,
' so no extra open/close is needed on a first run).
' ─────────────────────────────────────────────────────────────────────────────
Function IsAlreadyProcessed(sNewFull As String, sProject As String) As Boolean
    If Not System.IO.File.Exists(sNewFull) Then Return False
    Dim sExisting As String = ""
    Try
        ' Use already-open instance if available (zero overhead)
        Dim oDoc As Document = Nothing
        Try : oDoc = ThisApplication.Documents.ItemByName(sNewFull) : Catch : End Try
        If oDoc IsNot Nothing Then
            Try
                sExisting = oDoc.PropertySets( _
                    "Inventor User Defined Properties").Item("CS_CopyProject").Value
            Catch : End Try
        Else
            ' File exists on disk but is not open — open it briefly
            Dim bPrevSilent As Boolean = ThisApplication.SilentOperation
            ThisApplication.SilentOperation = True
            Try
                Dim oTmp As Document = ThisApplication.Documents.Open(sNewFull, False)
                Try
                    sExisting = oTmp.PropertySets( _
                        "Inventor User Defined Properties").Item("CS_CopyProject").Value
                Catch : End Try
                Try : oTmp.Close(True) : Catch : End Try
            Catch
            Finally
                ThisApplication.SilentOperation = bPrevSilent
            End Try
        End If
    Catch : End Try
    Return (String.Compare(sExisting, sProject, True) = 0)
End Function


' ─────────────────────────────────────────────────────────────────────────────
' HELPER: Walk assembly tree and build old->new rename map
' Visits every referenced .iam and .ipt, deepest children first.
' Files with no old-prefix match are excluded from the map.
' ─────────────────────────────────────────────────────────────────────────────
Sub WalkTree(oDoc As Document, _
             sOldPrefix As String, sNewPrefix As String, _
             sTargetFolder As String, _
             oRenameMap As System.Collections.Generic.Dictionary(Of String, String), _
             oSeen As System.Collections.Generic.HashSet(Of String), _
             sLogPath As String)

    Dim sFullPath As String = ""
    Try : sFullPath = oDoc.FullFileName : Catch : Return : End Try

    Dim sFullUpper As String = sFullPath.ToUpper()
    If oSeen.Contains(sFullUpper) Then Return
    oSeen.Add(sFullUpper)

    ' ── Recurse into referenced children first (deepest-first) ───────────────
    Try
        For Each oDesc As Object In oDoc.ReferencedDocumentDescriptors
            Dim sRefPath As String = ""
            Try : sRefPath = oDesc.FullDocumentName : Catch : Continue For : End Try

            ' Strip DART SHUT state tag e.g. "C:\path\file.iam<DART SHUT>"
            Dim iAngle As Integer = sRefPath.IndexOf("<"c)
            If iAngle > 0 Then sRefPath = sRefPath.Substring(0, iAngle)
            sRefPath = sRefPath.Trim()
            If sRefPath = "" Then Continue For

            Dim sRefExt As String = System.IO.Path.GetExtension(sRefPath).ToUpper()
            If sRefExt <> ".IAM" AndAlso sRefExt <> ".IPT" Then Continue For
            If Not System.IO.File.Exists(sRefPath) Then Continue For

            ' F3: Skip Content Centre parts — SaveAs on a CC part detaches
            ' it from the Content Centre and corrupts its metadata bindings.
            ' Check both the document sub-type and a path heuristic for
            ' environments where CC files may not be open yet.
            If sRefPath.ToUpper().Contains("CONTENT CENTER") Then Continue For

            If oSeen.Contains(sRefPath.ToUpper()) Then Continue For

            ' Open child (or reuse already-open instance)
            Dim oChild As Document = Nothing
            Try : oChild = ThisApplication.Documents.ItemByName(sRefPath) : Catch : End Try
            If oChild Is Nothing Then
                Try
                    oChild = ThisApplication.Documents.Open(sRefPath, False)
                Catch exOpen As Exception
                    Try
                        System.IO.File.AppendAllText(sLogPath, _
                            "WALK-OPEN-FAIL: " & System.IO.Path.GetFileName(sRefPath) & _
                            " — " & exOpen.Message & vbCrLf)
                    Catch : End Try
                    Continue For
                End Try
            End If

            ' F3: Sub-type check on the open document (most reliable CC guard)
            Try
                If oChild.DocumentSubType = kCCPartDocumentSubType Then
                    Try
                        System.IO.File.AppendAllText(sLogPath, _
                            "WALK-CC-SKIP: " & System.IO.Path.GetFileName(sRefPath) & vbCrLf)
                    Catch : End Try
                    Continue For
                End If
            Catch : End Try  ' DocumentSubType may not be supported on all types

            WalkTree(oChild, sOldPrefix, sNewPrefix, sTargetFolder, _
                     oRenameMap, oSeen, sLogPath)
        Next
    Catch exWalk As Exception
        Try
            System.IO.File.AppendAllText(sLogPath, _
                "WALK-DESC-FAIL: " & System.IO.Path.GetFileName(sFullPath) & _
                " — " & exWalk.Message & vbCrLf)
        Catch : End Try
    End Try

    ' ── Compute new name for THIS document ───────────────────────────────────
    Dim sBase As String = System.IO.Path.GetFileNameWithoutExtension(sFullPath)
    Dim sExt  As String = System.IO.Path.GetExtension(sFullPath)

    ' Only rename files whose basename starts with the old prefix
    If Not sBase.ToUpper().StartsWith(sOldPrefix.ToUpper()) Then Return

    Dim sNewBase As String = sNewPrefix & sBase.Substring(sOldPrefix.Length)
    Dim sNewFull As String = System.IO.Path.Combine(sTargetFolder, sNewBase & sExt)

    If String.Compare(sFullPath, sNewFull, True) <> 0 Then
        If Not oRenameMap.ContainsKey(sFullPath) Then
            oRenameMap(sFullPath) = sNewFull
            Try
                System.IO.File.AppendAllText(sLogPath, _
                    "MAP: " & sBase & sExt & "  ->  " & sNewBase & sExt & vbCrLf)
            Catch : End Try
        End If
    End If
End Sub


' ─────────────────────────────────────────────────────────────────────────────
' SUB MAIN
' ─────────────────────────────────────────────────────────────────────────────
Sub Main()

    ' ── 0. Validate active document ──────────────────────────────────────────
    Dim oAsmDoc As AssemblyDocument = TryCast(ThisApplication.ActiveDocument, AssemblyDocument)
    If oAsmDoc Is Nothing Then
        MessageBox.Show( _
            "Open the top-level GA assembly first, then run Super Clean Sweeper.", _
            "Super Clean Sweeper")
        Exit Sub
    End If
    Dim sTopFull As String = oAsmDoc.FullFileName
    Dim sTopBase As String = System.IO.Path.GetFileNameWithoutExtension(sTopFull)
    Dim sTopExt  As String = System.IO.Path.GetExtension(sTopFull)

    ' ── 1. Set up log file on Desktop ────────────────────────────────────────
    Dim sDesktop As String = System.Environment.GetFolderPath( _
        System.Environment.SpecialFolder.Desktop)
    Dim sLogPath As String = System.IO.Path.Combine(sDesktop, _
        "SUPER_CLEAN_SWEEPER_" & Now.ToString("yyyyMMdd_HHmmss") & ".log")
    Dim sLog As String = "SUPER CLEAN SWEEPER  v1.0.0  —  " & Now.ToString() & vbCrLf & _
                         "GA: " & sTopFull & vbCrLf
    Try : System.IO.File.WriteAllText(sLogPath, sLog) : Catch : End Try

    ' ── 2. Suppress Inventor confirmation dialogs ─────────────────────────────
    Dim bOrigSilent As Boolean = ThisApplication.SilentOperation
    ThisApplication.SilentOperation = True

    ' ── 3. User: pick target folder ──────────────────────────────────────────
    ThisApplication.SilentOperation = bOrigSilent
    Dim oFbd As New FolderBrowserDialog()
    oFbd.Description = "Select destination folder for the new assembly copies  (the _CLEAN folder)"
    oFbd.SelectedPath = System.IO.Path.GetDirectoryName(sTopFull)
    If oFbd.ShowDialog() <> DialogResult.OK Then
        MessageBox.Show("Cancelled — no changes made.", "Super Clean Sweeper")
        Exit Sub
    End If
    Dim sTargetFolder As String = oFbd.SelectedPath
    ThisApplication.SilentOperation = True

    ' ── 4. Detect old prefix; ask for new prefix ─────────────────────────────
    Dim sOldPrefix As String = ""
    Dim iDash As Integer = sTopBase.IndexOf("-"c)
    If iDash > 0 Then sOldPrefix = sTopBase.Substring(0, iDash)

    ThisApplication.SilentOperation = bOrigSilent
    Dim sNewPrefix As String = InputBox( _
        "Detected current prefix: """ & sOldPrefix & """" & vbCrLf & vbCrLf & _
        "Enter the NEW project prefix (e.g. PJ00222):" & vbCrLf & _
        "(Only files whose name STARTS WITH the old prefix will be copied.)", _
        "Super Clean Sweeper — New Prefix", sOldPrefix)
    sNewPrefix = Trim(sNewPrefix)
    If sNewPrefix = "" Then
        MessageBox.Show("Cancelled — no prefix entered.", "Super Clean Sweeper")
        Exit Sub
    End If
    If String.Compare(sOldPrefix, sNewPrefix, True) = 0 Then
        Dim oSameRes As DialogResult = MessageBox.Show( _
            "Old and new prefix are the same (" & sOldPrefix & ")." & vbCrLf & _
            "Files will be SaveAs'd to the target folder without renaming." & vbCrLf & vbCrLf & _
            "Continue?", "Super Clean Sweeper — Same Prefix", _
            MessageBoxButtons.YesNo, MessageBoxIcon.Warning)
        If oSameRes <> DialogResult.Yes Then Exit Sub
    End If
    ThisApplication.SilentOperation = True

    Try : System.IO.File.AppendAllText(sLogPath, _
        "Target : " & sTargetFolder & vbCrLf & _
        "OldPfx : " & sOldPrefix & "   NewPfx : " & sNewPrefix & vbCrLf) : Catch : End Try

    ' Ensure target folder exists
    If Not System.IO.Directory.Exists(sTargetFolder) Then
        Try
            System.IO.Directory.CreateDirectory(sTargetFolder)
        Catch exDir As Exception
            ThisApplication.SilentOperation = bOrigSilent
            MessageBox.Show("Could not create target folder:" & vbCrLf & exDir.Message, _
                "Super Clean Sweeper")
            Exit Sub
        End Try
    End If

    ' ── 5. PHASE 1 — Build rename map ────────────────────────────────────────
    Try : System.IO.File.AppendAllText(sLogPath, vbCrLf & "=== PHASE 1: RENAME MAP ===" & vbCrLf) : Catch : End Try

    Dim oRenameMap As New System.Collections.Generic.Dictionary(Of String, String)( _
        StringComparer.OrdinalIgnoreCase)
    Dim oSeen As New System.Collections.Generic.HashSet(Of String)( _
        StringComparer.OrdinalIgnoreCase)

    Try
        WalkTree(oAsmDoc, sOldPrefix, sNewPrefix, sTargetFolder, _
                 oRenameMap, oSeen, sLogPath)
    Catch exWalk As Exception
        ThisApplication.SilentOperation = bOrigSilent
        MessageBox.Show("Phase 1 walk failed: " & exWalk.Message, "Super Clean Sweeper")
        Exit Sub
    End Try

    ' Add the top assembly itself
    If sTopBase.ToUpper().StartsWith(sOldPrefix.ToUpper()) Then
        Dim sTopNewBase As String = sNewPrefix & sTopBase.Substring(sOldPrefix.Length)
        Dim sTopNewFull As String = System.IO.Path.Combine(sTargetFolder, sTopNewBase & sTopExt)
        If String.Compare(sTopFull, sTopNewFull, True) <> 0 Then
            If Not oRenameMap.ContainsKey(sTopFull) Then
                oRenameMap(sTopFull) = sTopNewFull
                Try : System.IO.File.AppendAllText(sLogPath, _
                    "MAP (TOP): " & sTopBase & sTopExt & "  ->  " & sTopNewBase & sTopExt & vbCrLf) : Catch : End Try
            End If
        End If
    End If

    Try : System.IO.File.AppendAllText(sLogPath, _
        "Phase 1 complete: " & oRenameMap.Count & " file(s) in map." & vbCrLf) : Catch : End Try

    If oRenameMap.Count = 0 Then
        ThisApplication.SilentOperation = bOrigSilent
        MessageBox.Show("No files found with prefix '" & sOldPrefix & "'." & vbCrLf & _
            "Check the GA is open and the prefix matches its filename.", _
            "Super Clean Sweeper — Nothing to do")
        Exit Sub
    End If

    ' Confirm with user before making changes
    ThisApplication.SilentOperation = bOrigSilent
    Dim oConfirm As DialogResult = MessageBox.Show( _
        oRenameMap.Count & " file(s) will be processed:" & vbCrLf & _
        "• SaveAs (fresh GUID) → " & sTargetFolder & vbCrLf & _
        "• Provenance properties written (CS_SourcePath, CS_SourceGUID, etc.)" & vbCrLf & _
        "• Original files are NOT modified" & vbCrLf & vbCrLf & _
        "Proceed?", _
        "Super Clean Sweeper — Confirm", _
        MessageBoxButtons.YesNo, MessageBoxIcon.Question)
    If oConfirm <> DialogResult.Yes Then
        MessageBox.Show("Cancelled — no changes made.", "Super Clean Sweeper")
        Exit Sub
    End If
    ThisApplication.SilentOperation = True

    ' ── 6. PHASE 2 — SaveAs + Provenance ─────────────────────────────────────
    ' F1: Wrap Phase 2 + 3 in Try/Finally so SilentOperation is ALWAYS
    ' restored even if an unexpected exception escapes the per-file catches.
    ' Process in deepest-first order: sort by OLD path length descending
    ' (deeper paths are longer; this ensures children are saved before parents).
    Try : System.IO.File.AppendAllText(sLogPath, vbCrLf & "=== PHASE 2: SAVEAS + PROVENANCE ===" & vbCrLf) : Catch : End Try
    Try  ' ← F1: outer Try/Finally begins here — Finally restores SilentOperation

    Dim oMapKeys As New System.Collections.Generic.List(Of String)(oRenameMap.Keys)
    oMapKeys.Sort(Function(a2, b2) b2.Length.CompareTo(a2.Length))

    Dim iSaved       As Integer = 0
    Dim iSkipped     As Integer = 0
    Dim iSaveFailed  As Integer = 0
    ' Track files actually placed on disk (Phase 3 uses this map)
    Dim oActualMap As New System.Collections.Generic.Dictionary(Of String, String)( _
        StringComparer.OrdinalIgnoreCase)

    Dim sOldFull2 As String
    For Each sOldFull2 In oMapKeys
        Dim sNewFull2  As String = oRenameMap(sOldFull2)
        Dim sOldName2  As String = System.IO.Path.GetFileName(sOldFull2)
        Dim sNewName2  As String = System.IO.Path.GetFileName(sNewFull2)
        Dim sExtU2     As String = System.IO.Path.GetExtension(sOldFull2).ToUpper()

        Try
            ' ── Provenance skip guard ────────────────────────────────────────
            If IsAlreadyProcessed(sNewFull2, sNewPrefix) Then
                iSkipped += 1
                oActualMap(sOldFull2) = sNewFull2
                Try : System.IO.File.AppendAllText(sLogPath, _
                    "PROV-SKIP: " & sOldName2 & vbCrLf) : Catch : End Try
                Continue For
            End If

            ' ── Source file must exist ───────────────────────────────────────
            If Not System.IO.File.Exists(sOldFull2) Then
                iSaveFailed += 1
                Try : System.IO.File.AppendAllText(sLogPath, _
                    "SKIP-MISSING: " & sOldName2 & vbCrLf) : Catch : End Try
                Continue For
            End If

            ' ── Clear read-only on source ─────────────────────────────────────
            Try
                Dim oA As System.IO.FileAttributes = System.IO.File.GetAttributes(sOldFull2)
                If (oA And System.IO.FileAttributes.ReadOnly) = System.IO.FileAttributes.ReadOnly Then
                    System.IO.File.SetAttributes(sOldFull2, oA And Not System.IO.FileAttributes.ReadOnly)
                End If
            Catch : End Try

            ' ── Ensure destination directory exists ──────────────────────────
            Dim sDestDir2 As String = System.IO.Path.GetDirectoryName(sNewFull2)
            If Not System.IO.Directory.Exists(sDestDir2) Then
                Try : System.IO.Directory.CreateDirectory(sDestDir2) : Catch : End Try
            End If

            ' ── Open source document ─────────────────────────────────────────
            Dim oDoc2 As Document = Nothing
            Try : oDoc2 = ThisApplication.Documents.ItemByName(sOldFull2) : Catch : End Try
            Dim bOpenedHere2 As Boolean = False
            If oDoc2 Is Nothing Then
                Try
                    oDoc2 = ThisApplication.Documents.Open(sOldFull2, False)
                    bOpenedHere2 = True
                Catch exOpen2 As Exception
                    iSaveFailed += 1
                    Try : System.IO.File.AppendAllText(sLogPath, _
                        "OPEN-FAIL: " & sOldName2 & " — " & exOpen2.Message & vbCrLf) : Catch : End Try
                    Continue For
                End Try
            End If

            ' ── Capture GUID BEFORE SaveAs ───────────────────────────────────
            ' InternalName returns the file's GUID.  SaveAs creates a NEW GUID
            ' in the saved copy; we capture the OLD one here so it can be
            ' written as CS_SourceGUID in the new file's iProperties.
            Dim sOldGUID2 As String = ""
            Try : sOldGUID2 = oDoc2.InternalName : Catch : End Try

            ' ── Collect old model refs from drawings ─────────────────────────
            ' For .idw / .dwg: record every referenced model path BEFORE the copy.
            ' Written to CS_ModelRefs on the new drawing (pipe-delimited).
            Dim oModelRefs2 As New System.Collections.Generic.List(Of String)()
            If sExtU2 = ".IDW" OrElse sExtU2 = ".DWG" Then
                Try
                    For Each oDesc2 As Object In oDoc2.ReferencedDocumentDescriptors
                        Dim sRef2 As String = ""
                        Try : sRef2 = oDesc2.FullDocumentName : Catch : Continue For : End Try
                        Dim iAng2 As Integer = sRef2.IndexOf("<"c)
                        If iAng2 > 0 Then sRef2 = sRef2.Substring(0, iAng2)
                        sRef2 = sRef2.Trim()
                        If sRef2 <> "" Then oModelRefs2.Add(sRef2)
                    Next
                Catch : End Try
            End If

            ' ── SaveAs to new path (SaveCopyAs = True) ───────────────────────
            ' SaveCopyAs=True: writes a new independent copy to sNewFull2 and
            ' assigns it a fresh GUID.  The current doc instance stays bound
            ' to the ORIGINAL path — originals are never touched.
            Dim bSaveAsOk2 As Boolean = False
            Try
                oDoc2.SaveAs(sNewFull2, True)
                bSaveAsOk2 = System.IO.File.Exists(sNewFull2)
            Catch exSA2 As Exception
                Try : System.IO.File.AppendAllText(sLogPath, _
                    "SAVEAS-FAIL: " & sOldName2 & " — " & exSA2.Message & vbCrLf) : Catch : End Try
            End Try

            If bSaveAsOk2 Then
                ' Clear RO on new file
                Try
                    Dim oNA2 As System.IO.FileAttributes = System.IO.File.GetAttributes(sNewFull2)
                    If (oNA2 And System.IO.FileAttributes.ReadOnly) = System.IO.FileAttributes.ReadOnly Then
                        System.IO.File.SetAttributes(sNewFull2, oNA2 And Not System.IO.FileAttributes.ReadOnly)
                    End If
                Catch : End Try

                ' ── Open new file and write provenance ───────────────────────
                ' SaveCopyAs=True does NOT leave the new file open in Inventor.
                ' We must open it, write provenance props, save, then close.
                Dim oNewDoc2 As Document = Nothing
                Try
                    oNewDoc2 = ThisApplication.Documents.Open(sNewFull2, False)
                Catch exOpenNew2 As Exception
                    Try : System.IO.File.AppendAllText(sLogPath, _
                        "NEW-OPEN-FAIL: " & sNewName2 & " — " & exOpenNew2.Message & vbCrLf) : Catch : End Try
                End Try

                If oNewDoc2 IsNot Nothing Then
                    ' Write CS_SourcePath, CS_SourceName, CS_CopyProject,
                    ' CS_CopyDate, CS_SourceGUID
                    WriteProvenanceProps(oNewDoc2, sOldFull2, sNewPrefix, sOldGUID2, sLogPath)

                    ' Write CS_ModelRefs for drawing files
                    If (sExtU2 = ".IDW" OrElse sExtU2 = ".DWG") AndAlso _
                       oModelRefs2.Count > 0 Then
                        WriteDrawingModelRefs(oNewDoc2, oModelRefs2, sLogPath)
                    End If

                    ' Save provenance to disk
                    Try
                        oNewDoc2.Save()
                    Catch exSvProv2 As Exception
                        Try : System.IO.File.AppendAllText(sLogPath, _
                            "PROV-SAVE-FAIL: " & sNewName2 & " — " & exSvProv2.Message & vbCrLf) : Catch : End Try
                    End Try

                    ' Close the new file (Phase 3 will reopen .iam/.ipt if needed)
                    Try : oNewDoc2.Close(True) : Catch : End Try

                    Try : System.IO.File.AppendAllText(sLogPath, _
                        "SAVED+PROV: " & sOldName2 & "  ->  " & sNewName2 & _
                        "  [OldGUID:" & sOldGUID2 & "]" & vbCrLf) : Catch : End Try
                End If

                oActualMap(sOldFull2) = sNewFull2
                iSaved += 1
            Else
                iSaveFailed += 1
            End If

            ' ── Close source if we opened it ─────────────────────────────────
            If bOpenedHere2 AndAlso oDoc2 IsNot Nothing Then
                Try : oDoc2.Close(True) : Catch : End Try
            End If

        Catch exOuter2 As Exception
            iSaveFailed += 1
            Try : System.IO.File.AppendAllText(sLogPath, _
                "P2-ERROR: " & sOldName2 & " — " & exOuter2.Message & vbCrLf) : Catch : End Try
        End Try
    Next

    Try : System.IO.File.AppendAllText(sLogPath, _
        "Phase 2 complete: " & iSaved & " saved, " & _
        iSkipped & " prov-skipped, " & iSaveFailed & " failed." & vbCrLf) : Catch : End Try

    ' ── 7. PHASE 3 — Fix internal references in new files ────────────────────
    ' Each new .iam / .ipt was SaveAs'd from the original, so its FileDescriptors
    ' still point at the OLD paths.  Open each new file and rewrite FDs to new
    ' paths using the actual map.  Deepest-first so nested assemblies are
    ' consistent before their parents are saved.
    Try : System.IO.File.AppendAllText(sLogPath, vbCrLf & "=== PHASE 3: FIX INTERNAL REFS ===" & vbCrLf) : Catch : End Try

    ' Collect unique new paths (avoid processing the same file twice)
    Dim oNewSet As New System.Collections.Generic.HashSet(Of String)( _
        StringComparer.OrdinalIgnoreCase)
    Dim sActualVal As String
    For Each sActualVal In oActualMap.Values
        oNewSet.Add(sActualVal)
    Next
    Dim oNewSorted As New System.Collections.Generic.List(Of String)(oNewSet)
    oNewSorted.Sort(Function(a2, b2) b2.Length.CompareTo(a2.Length))

    Dim iRefFixed  As Integer = 0
    Dim iRefFailed As Integer = 0
    Dim sNewPath3  As String

    For Each sNewPath3 In oNewSorted
        Dim sNewName3 As String = System.IO.Path.GetFileName(sNewPath3)
        Dim sExtU3    As String = System.IO.Path.GetExtension(sNewPath3).ToUpper()

        ' Only .iam and .ipt have internal file references to rewrite
        If sExtU3 <> ".IAM" AndAlso sExtU3 <> ".IPT" Then Continue For
        If Not System.IO.File.Exists(sNewPath3) Then Continue For

        Dim bOpened3 As Boolean = False
        Dim oDoc3    As Document = Nothing
        Try
            Try : oDoc3 = ThisApplication.Documents.ItemByName(sNewPath3) : Catch : End Try
            If oDoc3 Is Nothing Then
                Try
                    oDoc3 = ThisApplication.Documents.Open(sNewPath3, False)
                    bOpened3 = True
                Catch exOpen3 As Exception
                    Try : System.IO.File.AppendAllText(sLogPath, _
                        "P3-OPEN-FAIL: " & sNewName3 & " — " & exOpen3.Message & vbCrLf) : Catch : End Try
                    Continue For
                End Try
            End If

            Dim bChanged3 As Boolean = False
            Try
                ' F2: Null-check oDoc3.File before accessing ReferencedFileDescriptors.
                ' On unresolved or error-state documents, .File can be Nothing, causing
                ' a NullReferenceException caught only by the outer exP3 catch.
                If oDoc3.File Is Nothing Then
                    Try : System.IO.File.AppendAllText(sLogPath, _
                        "P3-FILE-NULL: " & sNewName3 & vbCrLf) : Catch : End Try
                    Continue For
                End If
                For Each oFD3 As Object In oDoc3.File.ReferencedFileDescriptors
                    Dim sOldRef3 As String = ""
                    Try : sOldRef3 = oFD3.FullFileName : Catch : Continue For : End Try

                    If Not oActualMap.ContainsKey(sOldRef3) Then Continue For
                    Dim sNewRef3 As String = oActualMap(sOldRef3)
                    If Not System.IO.File.Exists(sNewRef3) Then Continue For
                    If String.Compare(sOldRef3, sNewRef3, True) = 0 Then Continue For

                    Try
                        oFD3.ReplaceReference(sNewRef3)
                        bChanged3 = True
                        iRefFixed += 1
                        Try : System.IO.File.AppendAllText(sLogPath, _
                            "  P3-FD: " & System.IO.Path.GetFileName(sOldRef3) & _
                            "  ->  " & System.IO.Path.GetFileName(sNewRef3) & vbCrLf) : Catch : End Try
                    Catch exFD3 As Exception
                        iRefFailed += 1
                        Try : System.IO.File.AppendAllText(sLogPath, _
                            "  P3-FD-FAIL: " & System.IO.Path.GetFileName(sOldRef3) & _
                            " — " & exFD3.Message & vbCrLf) : Catch : End Try
                    End Try
                Next
            Catch exFDWalk3 As Exception
                Try : System.IO.File.AppendAllText(sLogPath, _
                    "P3-FD-WALK-FAIL: " & sNewName3 & " — " & exFDWalk3.Message & vbCrLf) : Catch : End Try
            End Try

            If bChanged3 Then
                Try
                    oDoc3.Save()
                    Try : System.IO.File.AppendAllText(sLogPath, _
                        "P3-SAVED: " & sNewName3 & vbCrLf) : Catch : End Try
                Catch exSv3 As Exception
                    Try : System.IO.File.AppendAllText(sLogPath, _
                        "P3-SAVE-FAIL: " & sNewName3 & " — " & exSv3.Message & vbCrLf) : Catch : End Try
                End Try
            End If

        Catch exP3 As Exception
            iRefFailed += 1
            Try : System.IO.File.AppendAllText(sLogPath, _
                "P3-ERROR: " & sNewName3 & " — " & exP3.Message & vbCrLf) : Catch : End Try
        Finally
            If bOpened3 AndAlso oDoc3 IsNot Nothing Then
                Try : oDoc3.Close(True) : Catch : End Try
            End If
        End Try
    Next

    Try : System.IO.File.AppendAllText(sLogPath, _
        "Phase 3 complete: " & iRefFixed & " fixed, " & iRefFailed & " failed." & vbCrLf) : Catch : End Try

    ' F1: Finally block — SilentOperation restored even if Phase 2/3 throws
    Finally
        ThisApplication.SilentOperation = bOrigSilent
    End Try  ' ← F1: outer Try/Finally ends here

    ' ── 8. SilentOperation already restored in Finally above ─────────────────

    ' ── 9. Final summary ──────────────────────────────────────────────────────
    Dim sSummary As String = _
        "SUPER CLEAN SWEEPER — COMPLETE" & vbCrLf & vbCrLf & _
        "Phase 1  Rename map built:   " & oRenameMap.Count & " file(s)" & vbCrLf & _
        "Phase 2  SaveAs + Provenance:" & vbCrLf & _
        "         Saved    : " & iSaved & vbCrLf & _
        "         Skipped  : " & iSkipped & "  (provenance guard — already processed)" & vbCrLf & _
        "         Failed   : " & iSaveFailed & vbCrLf & _
        "Phase 3  Ref fix  :" & vbCrLf & _
        "         Fixed    : " & iRefFixed & vbCrLf & _
        "         Failed   : " & iRefFailed & vbCrLf & vbCrLf & _
        "New files in : " & sTargetFolder & vbCrLf & _
        "Log          : " & sLogPath & vbCrLf & vbCrLf & _
        "NEXT STEPS" & vbCrLf & _
        "1. Open the new GA from the target folder to verify the assembly tree." & vbCrLf & _
        "2. Run the Drawing Relink pass to update drawings to new model paths" & vbCrLf & _
        "   (uses CS_ModelRefs + CS_SourcePath matching — no preset map needed)." & vbCrLf & _
        "3. Check the log for any SAVEAS-FAIL or P3-FD-FAIL entries."

    Try : System.IO.File.AppendAllText(sLogPath, vbCrLf & sSummary) : Catch : End Try

    MessageBox.Show(sSummary, "Super Clean Sweeper — Complete", _
        MessageBoxButtons.OK, MessageBoxIcon.Information)

End Sub
