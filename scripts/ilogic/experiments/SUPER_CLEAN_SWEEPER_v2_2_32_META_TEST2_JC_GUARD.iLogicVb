'' =====================================================================
'' SUPER_CLEAN_SWEEPER.iLogicVb
'' Copy Design with full provenance architecture
'' Version: 2.2.32-META-TEST2 — 2026-11-13
''
'' V2.2.32
''   - Recover SaveAs silent failures using safe non-overwriting File.Copy.
''   - Phase 4 occurrence replacement: retry via file descriptor, verify result.
''   - Log detailed failed replacement paths and HRESULTs.
''   - Correct runtime log version labels.
''
'' V2.2.31
''   - Main SaveAs fallback now handles all exceptions (including E_FAIL),
''     verifies destination and never overwrites an existing file.
''   - File.Copy assemblies defer opening/provenance until reference repair.
''   - Orphan subtree copy has a matching fallback and writes provenance
''     on the destination, not the source.
''   - Orphan single-part copy also writes provenance on destination.
''   - Distinct stage logging and path-depth ordering for orphan subtree.
''   - Copy success is not treated as proof that references are resolved.
''
'' PURPOSE
''   Replicates Vault Copy Design outside of Vault.
''   Copies an ENTIRE GA assembly tree (all referenced .iam/.ipt under
''   the old project root folder) to a new folder with a new project
''   prefix, using SaveAs (not File.Copy) so every new file gets a
''   fresh internal GUID.  Provenance iProperties are written to every
''   new model file at save time (zero extra open/save cost since the
''   file is already in Inventor's session).
''
'' V2 CHANGES FROM V1
''   1. UNIVERSAL COPY: ALL .iam/.ipt under the old project root folder
''      are copied — not just files whose basename starts with the old
''      prefix.  This catches JC-prefixed library parts, unnamed parts,
''      WIP subfolder parts, Design Accelerator subs, etc.
''   2. SMART RENAME: Strip any existing PJ-style prefix from filename
''      before prepending new prefix.  Avoids double-prefixing on reruns.
''      Non-prefixed files simply get the new prefix prepended.
''   3. DELTA-PROVENANCE CHAIN (8 properties):
''         CS_SourcePath    = this-run source full path
''         CS_SourceName    = this-run source filename
''         CS_CopyProject   = new project prefix (e.g. PJ00222)
''         CS_CopyDate      = copy date (yyyy-MM-dd)
''         CS_SourceGUID    = this-run source GUID (pre-SaveAs)
''         CS_RootSource    = very first PJ##### origin full path
''         CS_RootGUID      = very first PJ##### origin GUID
''         CS_RunCount      = increments each rerun (1 on first run)
''   4. OLD PROJECT ROOT auto-detected from GA path: walk up path
''      segments to find the folder whose name starts with the old prefix.
''
'' V2.2.2
''   SilentOperation stays True for the whole of Phase 2/3 (five per-file
''   resets to False removed) so Vault does not pop the "Multiple files
''   have been updated in current session" dialog between files.  The
''   outer Finally still restores the original SilentOperation at the end.
''   Phase 3 saves with Save2(False) (fallback Save) so the save does not
''   cascade to dirty CC/library dependents.
''
'' V2.2.23
''   DRAWING LIST MASTER TEXTBOX: new-name boxes are keyed by the old model
''   basename (file name, case-insensitive), not the full path.  The first
''   appearance is the master, prefilled with the computed new name.  Later
''   appearances of that basename are read-only and mirror the master via
''   TextChanged.  On OK only the master box is read; that value is written
''   into the rename map for every included full path with the same basename.
''   A model that is not copied (already in the target folder, or Content
''   Center) stays a locked master, and later copies of that basename mirror it.
''   DRAWING RELINK DESCRIPTORS: the relink loop walks
''   ReferencedDocumentDescriptors (late-bound Object, no FileDescriptor
''   cast).  FullDocumentName has any "<...>" tag stripped, then the cleaned
''   path is looked up in oActualMap.  When the target exists,
''   ReplaceReference is called on descriptor.ReferencedFileDescriptor.
''   Success logs DWG-REPLACE; failure logs DWG-REPLACE-FAIL.  A drawing is
''   saved only when at least one reference was replaced.
''
'' V2.2.22
''   DRAWING LIST FORM LAYOUT: matches the old Traverse ShowDrawingModelRenameForm
''   layout — title "Drawing Model Renames — Models and New Names", header about
''   string rules, column headers CURRENT/NEW, scrollable panel, per-drawing
''   number + include checkbox (default ON) + filename, models in a FixedSingle
''   bordered panel (old -> new), first appearance editable with later repeats
''   read-only and TextChanged-synced to the master, footer "Include ALL
''   drawings" plus OK/Cancel.  Unchecked drawings are removed from oDwgList
''   (logged DWG-EXCLUDED) so the relink pass skips them; name overrides are
''   taken from the master box when any included drawing lists that model.
''   STRING RULES PREFILL: 5 Find/Replace rows with "->" arrows; rows 1-3
''   prefilled from DetectStringAnomalies (mismatched middle tokens,
''   double-prefix first; never the plain old->new prefix swap); rows 4-5
''   blank for custom entries.  Logged STRING-SUGGEST / STRING-DETECT-FAIL.
''
'' V2.2.21
''   DRAWING LIST DESCRIPTOR SCAN: the Drawing List folder scan reads each
''   drawing's refs through ReferencedDocumentDescriptors (FullDocumentName,
''   late-bound, no FileDescriptor cast) instead of ReferencedFileDescriptors,
''   fixing "Unable to cast COM object ... to interface type
''   Inventor.FileDescriptor" and including DART SHUT refs.  Any "<...>" tag
''   is stripped.  If the descriptor loop throws, the scan falls back to
''   ReferencedDocuments (logged DWGLIST-REF-FALLBACK); DWGLIST-REF-FAIL is
''   logged only when the fallback also throws.  The Drawing List form is
''   always shown when started from a drawing: drawings that scanned are
''   listed, and if none did the form says no model refs were found.
''
'' V2.2.20
''   DRAWING ENTRY SCAN: when started from a drawing, the GA model is found
''   through ReferencedDocumentDescriptors (FullDocumentName) instead of
''   ReferencedFileDescriptors, so DART SHUT references are included.  Any
''   text from the first "<" onward is stripped from the path.  The first
''   .iam wins (first .ipt as fallback).  If the descriptor loop fails, the
''   scan falls back to ReferencedDocuments.  Logged as "ENTRY-SCAN:
''   descriptors" or "ENTRY-SCAN: fallback ReferencedDocuments".
''
'' V2.2.19
''   DRAWING LIST POPUP: when started from a drawing, every .idw/.dwg in the
''   drawing's folder is opened invisibly (closed again if opened here) and
''   its referenced .iam/.ipt paths are collected.  A form "Drawing List —
''   Models and New Names" lists each drawing with one row per model: old
''   name (read-only) and new base name (editable, prefilled with the
''   automatic new name).  A model already listed under an earlier drawing
''   is shown grey and locked.  Cancel exits with no changes.  On OK, every
''   edited name goes into oNameOverrides (old model path -> new base name),
''   which replaces the automatic prefix swap and string rules for that
''   model in the rename map (WalkTree and the top GA).  Logged as
''   DWGLIST, DWG-NAME and DWG-NAME-INVALID.
''   DRAWING RELINK now runs on every drawing in the list (entry drawing
''   always included), repointing refs found in oActualMap; logged as
''   "DWG-RELINK: <drawing> n replaced".  A drawing is saved only when at
''   least one ref was replaced.
''
'' V2.2.18  (Code-Assassin fixes — 2026-11-05)
''   FINAL DEFAULT DESIGN VIEW: after the browser-rename pass and before the
''   drawing relink / COMPLETE dialog, the "Default" design view is activated
''   on the open top GA so the user sees Default when the rule finishes.
''   FIX 1 (MEDIUM): sKeepOpenGA is now checked BEFORE ActiveDocument so the
''     correct new GA is always targeted even when Inventor shifts focus during
''     the browser-rename or drawing-relink pass.
''   FIX 2 (LOW): ItemByName(sKeepOpenGA) is now wrapped in its own Try/Catch
''     so a closed-document COM error falls through to the ActiveDocument
''     fallback instead of collapsing the whole block as FINAL-DV-FAIL.
''   FIX 3 (LOW): "Default" design view looked up case-insensitively; also
''     accepts "Standard" (German Inventor) for locale safety.  If no matching
''     view is found, logs "FINAL-DV-SKIP" instead of throwing.
''
'' V2.2.17  (Code-Assassin fixes — 2026-11-05)
''   FIX 1 (HIGH): ResolveTarget no longer reuses an existing file on a
''     plain prefix collision.  An existing target is reused ONLY when its
''     CS_SourcePath exactly matches the current source.  A mismatch or a
''     blank CS_SourcePath adds a _N suffix, logged as
''     "SUFFIX: <file> (provenance mismatch)".  Phase 3 now skips any file
''     this run did not create (oCreatedThisRun), logged as
''     "P3-SKIP-NOT-CREATED: <file>", so it never saves another file.
''   FIX 2 (MEDIUM): row 1 of the string-replacement form starts blank;
''     the prefix swap is already done by ComputeNewName.
''   FIX 3 (MEDIUM, speed): oSourcePathCache (Sub Main scoped, passed
''     through WalkTree and ResolveTarget) caches CS_SourcePath reads.
''     ReadCSSourcePath checks the cache first; on a miss it reads from the
''     in-session document, else opens invisibly, reads, closes, and caches.
''   FIX 4 (LOW): if the suffix loop reaches 10000, "SUFFIX-EXHAUSTED: <base>"
''     is logged and ResolveTarget returns ""; both callers skip the file.
''   FIX 5 (LOW): string-rule Find/Replace is case-insensitive
''     (Regex.Replace with RegexOptions.IgnoreCase, find text escaped).
''
'' V2.2.16
''   DV-FAIL LOG: in the Phase 2 design-view activation block, the outer
''   Catch around Activate() now logs the failure as
''   "DV-FAIL: <new file> (<design view>) — <error message>" instead of
''   swallowing it silently.
''
'' V2.2.15
''   STRING-REPLACEMENT POPUP: before Phase 1 a form shows 3 Find/Replace
''   rows (row 1 prefilled old prefix -> new prefix).  Non-blank pairs are
''   applied (exact, case-sensitive) to each new base name after the prefix
''   swap.  Each pair is logged as "STRING-RULE: find -> replace".
''   Cancel exits with no changes.
''   REUSE ON PROVENANCE MATCH: when a target name already exists on disk,
''   its CS_SourcePath is read; if it equals the current source path the
''   existing file is reused with no suffix ("REUSE: <file> (provenance
''   match)").
''   SUFFIX ONLY FOR STRING-RULE COLLISIONS: a _N suffix is added only when a
''   string rule changed the name AND that name exists AND its
''   CS_SourcePath does not match ("SUFFIX: <file> (string-rule
''   collision)").  A plain prefix-swap name that collides is reused
''   ("REUSE: <file> (prefix collision, CS_SourcePath: ...)").  Two sources
''   mapping to the same name in one run still get a suffix ("SUFFIX:
''   <file> (in-run collision)").  Reused files are kept as-is: Phase 2
''   skips the SaveAs for them (REUSE-SKIP) and maps them for Phase 3/4.
''
'' V2.2.14
''   BROWSER-RENAME PASS: after Phase 4 and before the drawing relink, the
''   new top GA (reused if still open, else opened visibly and left open)
''   is walked recursively.  Each occurrence whose file is in the target
''   folder gets its browser Name set to that filename without extension,
''   logged as "BROWSER-RENAME: <old> -> <new>".  Names already equal to
''   the base name, or base name + ":n", are left alone.  If the base name
''   is taken by a sibling, "<base>:n" is used.  Only sub-assemblies in the
''   target folder are walked; each one with renames is saved with
''   Save2(False), and the GA is saved with Save2(False) if anything changed.
''   Runs with SilentOperation = True.
''
'' V2.2.13
''   DEFAULT DESIGN VIEW ON TOP GA: in the Phase 2 DV-ACTIVATE block, when
''   the file is the top GA (sOldFull2 = sTopFull, case-insensitive), the
''   source's design view is re-activated as the open view.  Inventor has no
''   direct SetAsDefault; the view active at save time is the one the file
''   opens in.  Logged as DV-DEFAULT (or DV-DEFAULT-FAIL).  Sub-assemblies
''   keep DV-ACTIVATE only.
''
'' V2.2.12
''   NEW GA LEFT OPEN: Phase 4 no longer closes the new top GA after the
''   live occurrence walk and P4-GA-SAVED save; it is left open and
''   "P4-GA-LEFT-OPEN: <filename>" is logged.  If the GA is only open
''   invisibly (e.g. opened by the pre-Phase 2 provenance rebuild), a view
''   is added so it shows on screen (P4-GA-SHOWN).  The outer Finally skips
''   the close for that document (sKeepOpenGA); other documents the rule
''   opened are still closed.  Drawing entry: the drawing is left open if it
''   was already open and closed only if the rule opened it (unchanged).
''
'' V2.2.11
''   DESIGN-VIEW PRESERVATION: Phase 2 captures the source .iam's active
''   design view representation before SaveAs, and after provenance is
''   written activates the same-named design view in the new .iam before
''   Save2(False), so the copy opens with the same colors, appearance
''   overrides and visibility.  Logged as DV-ACTIVATE.
''
'' V2.2.10
''   GA-FIRST ORDERING: Phase 2 processes the top GA first (moved to the
''   front of oMapKeys after the length sort), so a hang on a later child
''   still leaves the GA in the target folder.  Logged as PHASE 2 ORDER.
''
'' V2.2.9  (Code-Assassin fixes — 2026-11-05)
''   FIX A: bEntryDocOpenedHere flag + cleanup guards for all early Exit Sub
''           paths in the drawing entry path — prevents session leaks on cancel.
''   FIX B: oActiveDoc.ReferencedFileDescriptors For Each wrapped in Try/Catch
''           — guards COM exception on corrupt or Vault-locked drawings.
''   FIX C: Phase 2 provenance save changed from Save() to Save2(False)
''           — prevents cascading to dirty dependents / Vault multi-file dialog.
''   FIX D: Drawing Relink FD loop snapshots to List(Of FileDescriptor) first
''           — consistent with Phase 3/4; prevents COM collection-modified fault.
''   FIX E: oDwgR added to oProvRebuildOpened right after open
''           — F1 Finally closes it even on save failure or unexpected exception.
''   FIX F: oTargetByBase build uses *.iam + *.ipt GetFiles instead of *.*
''           — avoids indexing PDFs/DWGs/logs on large target folders (~10x speedup).
''
'' V2.2.8
''   DRAWING ENTRY POINT: the rule can be run from a GA drawing.  It takes
''   the drawing's first referenced .iam (else first .ipt) as the model,
''   opens it if needed, and runs Phase 1-4 on it.  Logged as
''   "ENTRY: Drawing — model is <path>".
''   DRAWING RELINK PASS: after Phase 4, the original drawing's
''   ReferencedFileDescriptors found in oActualMap (target on disk) are
''   repointed with ReplaceReference, the drawing is saved with
''   Save2(False), and "DWG-RELINK: n replaced" is logged.  The drawing is
''   closed only if the rule opened it.
''
'' V2.2.7
''   ELAPSED TIME: dtStart is captured right after the log file is created.
''   Just before the COMPLETE dialog the run time is written to the log as
''   "Elapsed: HH:MM:SS" and shown in the dialog as "Elapsed : HH:MM:SS".
''
'' V2.2.6
''   VAULT BROWSER REFRESH: just before the final COMPLETE dialog the rule
''   runs the "VaultRefresh" command (fallback "AppRefreshCmd") so the
''   Vault browser shows the new paths without a manual refresh.
''
'' V2.2.5
''   RERUN FIX: when Phase 1 finds 0 files, the script no longer exits
''   straight away.  It scans the target folder for .iam/.ipt, reads
''   CS_SourcePath from each (ItemByName if open, else opened invisibly
''   and closed again), and adds CS_SourcePath -> current path to
''   oActualMap.  If at least one entry is recovered the run continues so
''   Phase 4 can resweep the GA; if none, "Nothing to do" + Exit Sub.
''   Phase 4 also uses the active GA itself when it already sits in the
''   target folder.
''
'' V2.2.4
''   PHASE 4 LIVE RESWEEP: after Phase 3, opens the new top GA and walks its
''   ComponentOccurrences bottom-up (Phase4_WalkOccs).  Any occurrence still
''   pointing at an old path with a target in oActualMap / oTargetByBase is
''   swapped with ComponentOccurrence.Replace (unsuppress first, re-suppress
''   after); target-folder assemblies are saved with Save2(False).
''   Browser rename is deferred.
''   PHASE 3 SAVE: Save2(False) only, no fallback to Save().  A failed save
''   logs the exact Save2 error (P3-SAVE2-FAIL) and the document is left open
''   for a later retry.  Close only after a successful save when opened here.
''   Refs are counted as fixed only after a successful save.
''
'' V2.2.3  (Code-Assassin fixes — 2026-11-05)
''   FIX 1: PRE-PHASE 2 document lifecycle — opened files tracked in
''           oProvRebuildOpened and closed in the outer Finally block.
''           Prevents unbounded open-document accumulation on large projects.
''   FIX 2: PRE-PHASE 2 file scan restricted to .IAM/.IPT only.
''           Drawings (.IDW/.DWG) can't carry CS_SourcePath and risk Vault
''           dialogs on partially-relinked open.
''   FIX 3: PRE-PHASE 2 scan now limited to files whose basename matches an
''           expected new filename (from oRenameMap.Values), avoiding opening
''           hundreds of prior-run files unnecessarily.
''   FIX 4: WalkTree accepts oWalkOpened + oMappedTargets params.
''           Sub Main closes all Walk-opened docs before Phase 2 starts so
''           Phase 2 controls each document's lifecycle with bOpenedHere2.
''   FIX 5: Collision guard uses oMappedTargets HashSet (O(1)) instead of
''           Dictionary.ContainsValue (O(n)) — avoids O(n²) on large trees.
''   FIX 6: Phase 3 P3Targets scan filters oTargetByBase (already built)
''           instead of a redundant second GetFiles("*.iam") disk call.
''   FIX 7: TryCast(oDoc3, AssemblyDocument) null-chaining fixed with an
''           explicit null guard before accessing .ComponentDefinition.
''   FIX 8: Silent SaveAs success (no exception, file not found on disk)
''           now logged as SAVEAS-SILENT-FAIL for diagnosis.
''   FIX 9: Files saved without provenance (new-file open fails after
''           SaveAs) logged as SAVED-NO-PROV; iNoProvenance counter added
''           to the final summary.
''
'' KEY ARCHITECTURAL PRINCIPLES (preserved from v1)
''   - Sub Main is FIRST; all helpers are defined AFTER it.
''   - No module-level Dim declarations outside Sub/Function bodies.
''   - No Imports statements (System.IO etc. are pre-imported in iLogic).
''   - For Each loop variables declared As Object for non-primitive types.
''   - ThisApplication only accessed inside Sub/Function bodies.
''   - CC guard: skip only when IsContentMember=True AND path contains
''     "Content Center".  Non-std CC parts saved into a project folder
''     are treated as project files.
''   - Counters declared before outer Try block to avoid variable hiding.
''
'' PHASES
''   Phase 1  Build old->new rename map  (walk GA tree, no disk writes)
''   Phase 2  SaveAs + Provenance        (creates new files, writes props)
''   Phase 3  Fix internal references    (open new .iam/.ipt, rewrite FDs)
''   Phase 4  Live occurrence resweep on the new GA
''   Drawing relink (only when started from a GA drawing; every listed drawing)
'' =====================================================================


' ─────────────────────────────────────────────────────────────────────────────
' SUB MAIN
' ─────────────────────────────────────────────────────────────────────────────
Sub Main()

    ' ── 0. Validate active document ──────────────────────────────────────────
    ' v2.2.8: the rule can also be started from a GA drawing.  The drawing's main
    ' model (first .iam it references, else first .ipt) is used as the GA, and the
    ' drawing is relinked to the new model paths after Phase 4.
    Dim oAsmDoc As AssemblyDocument = Nothing
    Dim bFromDwg As Boolean = False
    Dim sDwgEntryPath As String = ""
    Dim sEntryLog As String = ""
    Dim oEntryDoc As Document = Nothing        ' FIX A: declared here so early exits can close it
    Dim bEntryDocOpenedHere As Boolean = False  ' FIX A: True when this rule opened oEntryDoc
    Dim oActiveDoc As Document = ThisApplication.ActiveDocument
    If oActiveDoc IsNot Nothing AndAlso oActiveDoc.DocumentType = DocumentTypeEnum.kDrawingDocumentObject Then
        bFromDwg = True
        sDwgEntryPath = oActiveDoc.FullFileName
        Dim sEntryModel As String = ""
        Dim sEntryIpt As String = ""
        ' v2.2.20: scan ReferencedDocumentDescriptors (includes DART SHUT refs);
        ' strip any <...> tag; fall back to ReferencedDocuments on failure.
        Dim oEntryDD As DocumentDescriptor
        Dim oEntryRefDoc As Document
        Dim sEntryFDPath As String
        Dim sEntryFDExt As String
        Dim iEntryLt As Integer
        Dim bEntryScanOK As Boolean = False
        Dim sEntryScan As String = ""
        Try  ' FIX B: guard COM exception on corrupt or Vault-locked drawing refs
            For Each oEntryDD In oActiveDoc.ReferencedDocumentDescriptors
                sEntryFDPath = ""
                sEntryFDExt = ""
                Try
                    sEntryFDPath = oEntryDD.FullDocumentName
                Catch
                End Try
                If sEntryFDPath Is Nothing Then
                    sEntryFDPath = ""
                End If
                iEntryLt = sEntryFDPath.IndexOf("<")
                If iEntryLt >= 0 Then
                    sEntryFDPath = sEntryFDPath.Substring(0, iEntryLt).Trim()
                End If
                Try
                    sEntryFDExt = System.IO.Path.GetExtension(sEntryFDPath).ToUpper()
                Catch
                End Try
                If sEntryFDExt = ".IAM" AndAlso sEntryModel = "" Then
                    sEntryModel = sEntryFDPath
                End If
                If sEntryFDExt = ".IPT" AndAlso sEntryIpt = "" Then
                    sEntryIpt = sEntryFDPath
                End If
            Next
            bEntryScanOK = True
            sEntryScan = "ENTRY-SCAN: descriptors" & vbCrLf
        Catch
        End Try
        If Not bEntryScanOK Then
            sEntryScan = "ENTRY-SCAN: fallback ReferencedDocuments" & vbCrLf
            Try
                For Each oEntryRefDoc In oActiveDoc.ReferencedDocuments
                    sEntryFDPath = ""
                    sEntryFDExt = ""
                    Try
                        sEntryFDPath = oEntryRefDoc.FullDocumentName
                    Catch
                    End Try
                    If sEntryFDPath Is Nothing Then
                        sEntryFDPath = ""
                    End If
                    iEntryLt = sEntryFDPath.IndexOf("<")
                    If iEntryLt >= 0 Then
                        sEntryFDPath = sEntryFDPath.Substring(0, iEntryLt).Trim()
                    End If
                    Try
                        sEntryFDExt = System.IO.Path.GetExtension(sEntryFDPath).ToUpper()
                    Catch
                    End Try
                    If sEntryFDExt = ".IAM" AndAlso sEntryModel = "" Then
                        sEntryModel = sEntryFDPath
                    End If
                    If sEntryFDExt = ".IPT" AndAlso sEntryIpt = "" Then
                        sEntryIpt = sEntryFDPath
                    End If
                Next
            Catch
            End Try
        End If
        sEntryLog = sEntryScan
        If sEntryModel = "" Then sEntryModel = sEntryIpt
        If sEntryModel <> "" Then
            Try  ' FIX A: ItemByName to check if already open
                oEntryDoc = ThisApplication.Documents.ItemByName(sEntryModel)
            Catch
            End Try
            If oEntryDoc Is Nothing Then
                Try
                    oEntryDoc = ThisApplication.Documents.Open(sEntryModel, False)
                    bEntryDocOpenedHere = True  ' FIX A: track so early exits can close it
                Catch
                End Try
            End If
            oAsmDoc = TryCast(oEntryDoc, AssemblyDocument)
            sEntryLog &= "ENTRY: Drawing — model is " & sEntryModel & vbCrLf
        End If
    Else
        oAsmDoc = TryCast(oActiveDoc, AssemblyDocument)
    End If
    If oAsmDoc Is Nothing Then
        If bEntryDocOpenedHere AndAlso oEntryDoc IsNot Nothing Then  ' FIX A
            Try : oEntryDoc.Close(True) : Catch : End Try
        End If
        MessageBox.Show( _
            "Open the top-level GA assembly first, then run Super Clean Sweeper.", _
            "Super Clean Sweeper")
        Exit Sub
    End If
    Dim sTopFull As String = oAsmDoc.FullFileName
    Dim sTopBase As String = System.IO.Path.GetFileNameWithoutExtension(sTopFull)
    Dim sTopExt  As String = System.IO.Path.GetExtension(sTopFull)

    ' ── 1. Set up log file on Desktop ────────────────────────────────────────
    Dim sDesktop As String = System.Environment.GetFolderPath( _
        System.Environment.SpecialFolder.Desktop)
    Dim sLogPath As String = System.IO.Path.Combine(sDesktop, _
        "SUPER_CLEAN_SWEEPER_" & Now.ToString("yyyyMMdd_HHmmss") & ".log")
    Dim sLog As String = "SUPER CLEAN SWEEPER  v2.2.32  —  " & Now.ToString() & vbCrLf & _
                         "GA: " & sTopFull & vbCrLf
    Try : System.IO.File.WriteAllText(sLogPath, sLog) : Catch : End Try
    If sEntryLog <> "" Then
        Try : System.IO.File.AppendAllText(sLogPath, sEntryLog) : Catch : End Try
    End If
    Dim dtStart As DateTime = Now

    ' ── 2. Suppress Inventor confirmation dialogs ─────────────────────────────
    Dim bOrigSilent As Boolean = ThisApplication.SilentOperation
    ThisApplication.SilentOperation = True

    ' ── 3. User: pick target folder ──────────────────────────────────────────
    ThisApplication.SilentOperation = bOrigSilent
    Dim oFbd As New FolderBrowserDialog()
    oFbd.Description = "Select destination folder for the new assembly copies  (the _CLEAN folder)"
    oFbd.SelectedPath = System.IO.Path.GetDirectoryName(sTopFull)
    If oFbd.ShowDialog() <> DialogResult.OK Then
        If bEntryDocOpenedHere AndAlso oEntryDoc IsNot Nothing Then  ' FIX A
            Try : oEntryDoc.Close(True) : Catch : End Try
        End If
        MessageBox.Show("Cancelled — no changes made.", "Super Clean Sweeper")
        Exit Sub
    End If
    Dim sTargetFolder As String = oFbd.SelectedPath
    ThisApplication.SilentOperation = True

    ' ── 3b. Run mode: Full sweep or Relink only (v2.2.27) ────────────────────
    Dim bRelinkOnly As Boolean = False
    ThisApplication.SilentOperation = bOrigSilent
    Dim oModeForm As New Form()
    oModeForm.Text = "Super Clean Sweeper — Run Mode"
    oModeForm.Width = 480
    oModeForm.Height = 220
    oModeForm.StartPosition = FormStartPosition.CenterScreen
    oModeForm.FormBorderStyle = FormBorderStyle.FixedDialog
    oModeForm.MaximizeBox = False
    oModeForm.MinimizeBox = False
    Dim oRadFull As New RadioButton()
    oRadFull.Text = "Full sweep (Phases 1–4 + relink)"
    oRadFull.Left = 20 : oRadFull.Top = 30 : oRadFull.Width = 420
    oRadFull.Checked = True
    oModeForm.Controls.Add(oRadFull)
    Dim oRadRelink As New RadioButton()
    oRadRelink.Text = "Relink only (clean GA already exists)"
    oRadRelink.Left = 20 : oRadRelink.Top = 60 : oRadRelink.Width = 420
    oModeForm.Controls.Add(oRadRelink)
    Dim oModeOk As New Button()
    oModeOk.Text = "OK" : oModeOk.DialogResult = DialogResult.OK
    oModeOk.Left = 280 : oModeOk.Top = 120 : oModeOk.Width = 80
    oModeForm.Controls.Add(oModeOk)
    oModeForm.AcceptButton = oModeOk
    Dim oModeCancel As New Button()
    oModeCancel.Text = "Cancel" : oModeCancel.DialogResult = DialogResult.Cancel
    oModeCancel.Left = 370 : oModeCancel.Top = 120 : oModeCancel.Width = 80
    oModeForm.Controls.Add(oModeCancel)
    oModeForm.CancelButton = oModeCancel
    If oModeForm.ShowDialog() <> DialogResult.OK Then
        If bEntryDocOpenedHere AndAlso oEntryDoc IsNot Nothing Then
            Try : oEntryDoc.Close(True) : Catch : End Try
        End If
        MessageBox.Show("Cancelled — no changes made.", "Super Clean Sweeper")
        Exit Sub
    End If
    bRelinkOnly = oRadRelink.Checked
    ThisApplication.SilentOperation = True
    If bRelinkOnly Then
        Try : System.IO.File.AppendAllText(sLogPath, "MODE: Relink only — map built from CS_SourcePath in target folder" & vbCrLf) : Catch : End Try
    Else
        Try : System.IO.File.AppendAllText(sLogPath, "MODE: Full sweep" & vbCrLf) : Catch : End Try
    End If


    ' ── 4. Detect old prefix; ask for new prefix ─────────────────────────────
    Dim sOldPrefix As String = ""
    Dim iDash As Integer = sTopBase.IndexOf("-"c)
    If iDash > 0 Then sOldPrefix = sTopBase.Substring(0, iDash)

    ThisApplication.SilentOperation = bOrigSilent
    Dim sNewPrefix As String = InputBox( _
        "Detected current prefix: """ & sOldPrefix & """" & vbCrLf & vbCrLf & _
        "Enter the NEW project prefix (e.g. PJ00222):" & vbCrLf & _
        "(ALL files under the old project root folder will be copied and" & vbCrLf & _
        " prefixed — not just files starting with the old prefix.)", _
        "Super Clean Sweeper — New Prefix", sOldPrefix)
    sNewPrefix = Trim(sNewPrefix)
    If sNewPrefix = "" Then
        If bEntryDocOpenedHere AndAlso oEntryDoc IsNot Nothing Then  ' FIX A
            Try : oEntryDoc.Close(True) : Catch : End Try
        End If
        MessageBox.Show("Cancelled — no prefix entered.", "Super Clean Sweeper")
        Exit Sub
    End If
    If String.Compare(sOldPrefix, sNewPrefix, True) = 0 Then
        Dim oSameRes As DialogResult = MessageBox.Show( _
            "Old and new prefix are the same (" & sOldPrefix & ")." & vbCrLf & _
            "Files will be SaveAs'd to the target folder without renaming." & vbCrLf & vbCrLf & _
            "Continue?", "Super Clean Sweeper — Same Prefix", _
            MessageBoxButtons.YesNo, MessageBoxIcon.Warning)
        If oSameRes <> DialogResult.Yes Then
            If bEntryDocOpenedHere AndAlso oEntryDoc IsNot Nothing Then  ' FIX A
                Try : oEntryDoc.Close(True) : Catch : End Try
            End If
            Exit Sub
        End If
    End If
    ThisApplication.SilentOperation = True

    Try : System.IO.File.AppendAllText(sLogPath, _
        "Target : " & sTargetFolder & vbCrLf & _
        "OldPfx : " & sOldPrefix & "   NewPfx : " & sNewPrefix & vbCrLf) : Catch : End Try

    ' ── 4b. Detect old project ROOT folder ───────────────────────────────────
    ' Walk up from GA location to find folder whose name starts with sOldPrefix.
    ' This is the boundary — only files under this folder get copied.
    Dim sOldProjectRoot As String = ""
    Dim sCandDir As String = System.IO.Path.GetDirectoryName(sTopFull)
    Do While sCandDir <> ""
        Dim sDirName As String = System.IO.Path.GetFileName(sCandDir)
        If sDirName.ToUpper().StartsWith(sOldPrefix.ToUpper()) Then
            sOldProjectRoot = sCandDir
            Exit Do
        End If
        Dim sParent As String = System.IO.Path.GetDirectoryName(sCandDir)
        If sParent = sCandDir Then Exit Do   ' reached drive root
        sCandDir = sParent
    Loop
    ' Fallback: use GA's containing folder as the project root
    If sOldProjectRoot = "" Then
        sOldProjectRoot = System.IO.Path.GetDirectoryName(sTopFull)
    End If
    Try : System.IO.File.AppendAllText(sLogPath, _
        "OldRoot: " & sOldProjectRoot & vbCrLf) : Catch : End Try

    ' Ensure target folder exists
    If Not System.IO.Directory.Exists(sTargetFolder) Then
        Try
            System.IO.Directory.CreateDirectory(sTargetFolder)
        Catch exDir As Exception
            ThisApplication.SilentOperation = bOrigSilent
            If bEntryDocOpenedHere AndAlso oEntryDoc IsNot Nothing Then  ' FIX A
                Try : oEntryDoc.Close(True) : Catch : End Try
            End If
            MessageBox.Show("Could not create target folder:" & vbCrLf & exDir.Message, _
                "Super Clean Sweeper")
            Exit Sub
        End Try
    End If

    ' ── 4c. String-replacement rules (v2.2.22) ───────────────────────────────
    ' Up to 5 Find/Replace pairs, applied to each new base name after the
    ' prefix swap.  Rows 1-3 may be prefilled from DetectStringAnomalies;
    ' rows 4-5 stay blank for custom entries.  Never prefill the plain
    ' old-prefix -> new-prefix swap (ComputeNewName already does that).
    Dim oStringRules As New System.Collections.Generic.List(Of String())()
    ThisApplication.SilentOperation = bOrigSilent
    Dim oRuleForm As New System.Windows.Forms.Form()
    oRuleForm.Text = "Super Clean Sweeper — String Replacements"
    oRuleForm.FormBorderStyle = System.Windows.Forms.FormBorderStyle.FixedDialog
    oRuleForm.StartPosition = System.Windows.Forms.FormStartPosition.CenterScreen
    oRuleForm.MaximizeBox = False
    oRuleForm.MinimizeBox = False
    oRuleForm.Width = 560
    oRuleForm.Height = 340
    Dim oRuleHint As New System.Windows.Forms.Label()
    oRuleHint.Text = "Optional segment replaces (up to 5) - applied AFTER prefix swap. Leave Find blank to skip a row."
    oRuleHint.Left = 15
    oRuleHint.Top = 12
    oRuleHint.Width = 520
    oRuleHint.Height = 30
    oRuleForm.Controls.Add(oRuleHint)
    Dim oFindHdr As New System.Windows.Forms.Label()
    oFindHdr.Text = "Find"
    oFindHdr.Left = 15
    oFindHdr.Top = 46
    oFindHdr.Width = 220
    oRuleForm.Controls.Add(oFindHdr)
    Dim oReplHdr As New System.Windows.Forms.Label()
    oReplHdr.Text = "Replace with"
    oReplHdr.Left = 250
    oReplHdr.Top = 46
    oReplHdr.Width = 220
    oRuleForm.Controls.Add(oReplHdr)
    Dim aFindBox(4) As System.Windows.Forms.TextBox
    Dim aReplBox(4) As System.Windows.Forms.TextBox
    Dim aArrowLbl(4) As System.Windows.Forms.Label
    Dim iRuleRow As Integer
    For iRuleRow = 0 To 4
        aFindBox(iRuleRow) = New System.Windows.Forms.TextBox()
        aFindBox(iRuleRow).Left = 15
        aFindBox(iRuleRow).Top = 70 + iRuleRow * 30
        aFindBox(iRuleRow).Width = 220
        oRuleForm.Controls.Add(aFindBox(iRuleRow))
        aArrowLbl(iRuleRow) = New System.Windows.Forms.Label()
        aArrowLbl(iRuleRow).Text = "->"
        aArrowLbl(iRuleRow).Left = 238
        aArrowLbl(iRuleRow).Top = 73 + iRuleRow * 30
        aArrowLbl(iRuleRow).Width = 20
        oRuleForm.Controls.Add(aArrowLbl(iRuleRow))
        aReplBox(iRuleRow) = New System.Windows.Forms.TextBox()
        aReplBox(iRuleRow).Left = 250
        aReplBox(iRuleRow).Top = 70 + iRuleRow * 30
        aReplBox(iRuleRow).Width = 220
        oRuleForm.Controls.Add(aReplBox(iRuleRow))
    Next
    ' Prefill rows 1-3 from tree anomaly detect; rows 4-5 stay blank.
    Dim oSRSuggest As System.Collections.Generic.List(Of String()) = Nothing
    Dim oSRPair As String()
    Dim iSRSug As Integer
    Try
        oSRSuggest = DetectStringAnomalies(oAsmDoc, sOldPrefix, sNewPrefix, 3)
    Catch exSRDetect As Exception
        Try : System.IO.File.AppendAllText(sLogPath, "STRING-DETECT-FAIL: " & exSRDetect.Message & vbCrLf) : Catch : End Try
        oSRSuggest = New System.Collections.Generic.List(Of String())()
    End Try
    If oSRSuggest IsNot Nothing Then
        iSRSug = 0
        For Each oSRPair In oSRSuggest
            If iSRSug > 2 Then Exit For
            If oSRPair Is Nothing Then Continue For
            If oSRPair.Length < 2 Then Continue For
            If Trim(oSRPair(0)) = "" Then Continue For
            If String.Compare(Trim(oSRPair(0)), sOldPrefix, True) = 0 AndAlso _
               String.Compare(Trim(oSRPair(1)), sNewPrefix, True) = 0 Then
                Continue For
            End If
            aFindBox(iSRSug).Text = oSRPair(0)
            aReplBox(iSRSug).Text = oSRPair(1)
            Try : System.IO.File.AppendAllText(sLogPath, "STRING-SUGGEST: " & oSRPair(0) & " -> " & oSRPair(1) & vbCrLf) : Catch : End Try
            iSRSug = iSRSug + 1
        Next
    End If
    Dim oRuleOk As New System.Windows.Forms.Button()
    oRuleOk.Text = "OK"
    oRuleOk.Left = 348
    oRuleOk.Top = 240
    oRuleOk.Width = 84
    oRuleOk.DialogResult = System.Windows.Forms.DialogResult.OK
    oRuleForm.Controls.Add(oRuleOk)
    Dim oRuleCancel As New System.Windows.Forms.Button()
    oRuleCancel.Text = "Cancel"
    oRuleCancel.Left = 440
    oRuleCancel.Top = 240
    oRuleCancel.Width = 84
    oRuleCancel.DialogResult = System.Windows.Forms.DialogResult.Cancel
    oRuleForm.Controls.Add(oRuleCancel)
    oRuleForm.AcceptButton = oRuleOk
    oRuleForm.CancelButton = oRuleCancel
    Dim oRuleRes As System.Windows.Forms.DialogResult = oRuleForm.ShowDialog()
    If oRuleRes <> System.Windows.Forms.DialogResult.OK Then
        Try : oRuleForm.Dispose() : Catch : End Try
        If bEntryDocOpenedHere AndAlso oEntryDoc IsNot Nothing Then  ' FIX A
            Try : oEntryDoc.Close(True) : Catch : End Try
        End If
        MessageBox.Show("Cancelled — no changes made.", "Super Clean Sweeper")
        Exit Sub
    End If
    Dim sRuleFind As String
    Dim sRuleRepl As String
    For iRuleRow = 0 To 4
        sRuleFind = aFindBox(iRuleRow).Text
        sRuleRepl = aReplBox(iRuleRow).Text
        If sRuleFind = "" Then Continue For
        If sRuleFind = sRuleRepl Then Continue For
        oStringRules.Add(New String() {sRuleFind, sRuleRepl})
        Try : System.IO.File.AppendAllText(sLogPath, "STRING-RULE: " & sRuleFind & " -> " & sRuleRepl & vbCrLf) : Catch : End Try
    Next
    Try : oRuleForm.Dispose() : Catch : End Try
    ThisApplication.SilentOperation = True

    ' ── 4d. Drawing List (v2.2.23): basename master textbox + new names ───────
    ' Only when started from a drawing.  Scans the drawing's folder for .idw/.dwg,
    ' lists each drawing's referenced models and lets the user set the new base
    ' name of each model.  The first box for a basename is the master; later
    ' boxes only mirror it.  On OK only the master text is used.
    Dim oDwgList As New System.Collections.Generic.List(Of String)()
    Dim oNameOverrides As New System.Collections.Generic.Dictionary(Of String, String)( _
        StringComparer.OrdinalIgnoreCase)
    Dim oDwgModels As New System.Collections.Generic.Dictionary(Of String, System.Collections.Generic.List(Of String))( _
        StringComparer.OrdinalIgnoreCase)
    ' oDrawingStateMatch: declared here (top-level, before both bFromDwg blocks) so it is
    ' visible inside the form-building block (~line 1382) AND in Phase B2 relink (~line 2603).
    Dim oDrawingStateMatch As New System.Collections.Generic.Dictionary(Of String, Boolean)( _
        StringComparer.OrdinalIgnoreCase)
    If bFromDwg AndAlso sDwgEntryPath <> "" Then
        Try : System.IO.File.AppendAllText(sLogPath, vbCrLf & "=== DRAWING LIST ===" & vbCrLf) : Catch : End Try
        Dim sDwgFolder As String = System.IO.Path.GetDirectoryName(sDwgEntryPath)
        Dim oDwgFiles As New System.Collections.Generic.List(Of String)()
        Dim sDLFile As String
        Try
            For Each sDLFile In System.IO.Directory.GetFiles(sDwgFolder, "*.idw", System.IO.SearchOption.TopDirectoryOnly)
                oDwgFiles.Add(sDLFile)
            Next
            For Each sDLFile In System.IO.Directory.GetFiles(sDwgFolder, "*.dwg", System.IO.SearchOption.TopDirectoryOnly)
                oDwgFiles.Add(sDLFile)
            Next
        Catch exDLDir As Exception
            Try : System.IO.File.AppendAllText(sLogPath, "DWGLIST-DIR-FAIL: " & exDLDir.Message & vbCrLf) : Catch : End Try
        End Try
        Dim bDLEntryFound As Boolean = False
        For Each sDLFile In oDwgFiles
            If String.Equals(sDLFile, sDwgEntryPath, StringComparison.OrdinalIgnoreCase) Then bDLEntryFound = True
        Next
        If Not bDLEntryFound Then oDwgFiles.Add(sDwgEntryPath)
        oDwgFiles.Sort(StringComparer.OrdinalIgnoreCase)

        ' v2.2.27: Detect native AutoCAD DWG files using the proper Inventor API:
        '   ThisApplication.FileManager.IsInventorDWG() returns False for native AutoCAD DWGs.
        ' For each AutoCAD DWG, open it briefly as a DrawingDocument (Inventor can open these
        ' read-only without launching AutoCAD), walk Sheet.AutoCADBlocks, and call
        ' oBlk.GetPromptTextValues() to find the DRAWING_DESCRIPTION_2 attribute value.
        ' The document is closed immediately after reading — no AutoCAD launch risk.
        Dim oAcadDwgs As New System.Collections.Generic.HashSet(Of String)(StringComparer.OrdinalIgnoreCase)
        Dim oAcadDwgDescs As New System.Collections.Generic.Dictionary(Of String, String)(StringComparer.OrdinalIgnoreCase)
        For Each sDLCheck As String In oDwgFiles
            If Not String.Equals(System.IO.Path.GetExtension(sDLCheck), ".dwg", StringComparison.OrdinalIgnoreCase) Then Continue For
            Try
                Dim bIsAcad As Boolean = False
                Try : bIsAcad = Not ThisApplication.FileManager.IsInventorDWG(sDLCheck) : Catch : End Try
                If Not bIsAcad Then Continue For

                oAcadDwgs.Add(sDLCheck)
                ' v2.2.29: Open via Inventor API and walk AutoCADBlocks/GetPromptTextValues.
                ' This matches the approach proven in the old Traverse rule.
                ' Fallback 1: ContainingDWGDocument COM (AcDbBlockReference/GetAttributes).
                ' Fallback 2: raw UTF-16LE byte scan (kept for files that fail to open).
                Dim sAcadDesc As String = ""
                Try
                    ' ── v2.2.29  METHOD 1: Inventor API — Sheets → AutoCADBlocks → GetPromptTextValues ──
                    ' Proven working in prior Traverse rule. Open the DWG as a DrawingDocument,
                    ' walk every sheet's AutoCADBlocks, ask each block for its tag/value arrays.
                    Dim oAcadDwg As DrawingDocument = Nothing
                    Dim bAcadOpened As Boolean = False
                    Dim sbApiTags As New System.Text.StringBuilder()
                    Try
                        oAcadDwg = TryCast(ThisApplication.Documents.Open(sDLCheck, False), DrawingDocument)
                        bAcadOpened = True
                        If oAcadDwg IsNot Nothing Then
                            For Each oSheet As Sheet In oAcadDwg.Sheets
                                Try
                                    For Each oBlk As AutoCADBlock In oSheet.AutoCADBlocks
                                        Dim oTags() As String = Nothing
                                        Dim oVals() As String = Nothing
                                        Try : oBlk.GetPromptTextValues(oTags, oVals) : Catch : Continue For : End Try
                                        If oTags IsNot Nothing AndAlso oVals IsNot Nothing Then
                                            For iT As Integer = 0 To oTags.Length - 1
                                                Dim sTagV As String = If(oTags(iT), "")
                                                Dim sValV As String = If(iT < oVals.Length, If(oVals(iT), ""), "")
                                                sbApiTags.Append(sTagV & "='" & sValV & "'; ")
                                                If String.Compare(sTagV, "DRAWING_DESCRIPTION_2", True) = 0 _
                                                   OrElse (sAcadDesc = "" AndAlso (sTagV.ToUpper().Contains("DESCRIPTION") OrElse sTagV.ToUpper().Contains("DRAWING"))) Then
                                                    sAcadDesc = Trim(sValV)
                                                End If
                                            Next
                                        End If
                                        If sAcadDesc <> "" Then Exit For
                                    Next
                                Catch : End Try
                                If sAcadDesc <> "" Then Exit For
                            Next
                        End If
                    Catch exApi As Exception
                        Try : System.IO.File.AppendAllText(sLogPath, "DWGLIST-AUTOCAD-API-FAIL: " & System.IO.Path.GetFileName(sDLCheck) & " " & exApi.Message & vbCrLf) : Catch : End Try
                    Finally
                        If bAcadOpened AndAlso oAcadDwg IsNot Nothing Then
                            Try : oAcadDwg.Close(False) : Catch : End Try
                        End If
                    End Try
                    If sbApiTags.Length > 0 Then
                        Try : System.IO.File.AppendAllText(sLogPath, "DWGLIST-AUTOCAD-API-TAGS: " & System.IO.Path.GetFileName(sDLCheck) & " : " & sbApiTags.ToString() & vbCrLf) : Catch : End Try
                    Else
                        Try : System.IO.File.AppendAllText(sLogPath, "DWGLIST-AUTOCAD-API-TAGS: " & System.IO.Path.GetFileName(sDLCheck) & " : (no AutoCADBlocks / no tags)" & vbCrLf) : Catch : End Try
                    End If

                    ' ── v2.2.29  METHOD 2: ContainingDWGDocument COM (AcDbBlockReference/GetAttributes) ──
                    If sAcadDesc = "" Then
                        Dim oAcadDwg2 As DrawingDocument = Nothing
                        Dim bAcadOpened2 As Boolean = False
                        Dim sbDbTags As New System.Text.StringBuilder()
                        Try
                            oAcadDwg2 = TryCast(ThisApplication.Documents.Open(sDLCheck, False), DrawingDocument)
                            bAcadOpened2 = True
                            If oAcadDwg2 IsNot Nothing Then
                                Dim oAcadDb As Object = oAcadDwg2.ContainingDWGDocument
                                If oAcadDb IsNot Nothing Then
                                    Dim oLayouts As Object = Nothing
                                    Try : oLayouts = oAcadDb.Layouts : Catch : End Try
                                    If oLayouts IsNot Nothing Then
                                        For Each oLayout As Object In oLayouts
                                            Dim oBlkRec As Object = Nothing
                                            Try : oBlkRec = oLayout.Block : Catch : Continue For : End Try
                                            If oBlkRec Is Nothing Then Continue For
                                            For Each oEnt As Object In oBlkRec
                                                Dim sObjName As String = ""
                                                Try : sObjName = CStr(oEnt.ObjectName) : Catch : End Try
                                                If sObjName = "AcDbBlockReference" Then
                                                    Dim oAtts As Object = Nothing
                                                    Try : oAtts = oEnt.GetAttributes() : Catch : End Try
                                                    If oAtts IsNot Nothing Then
                                                        For Each oAtt As Object In oAtts
                                                            Dim sTagC As String = ""
                                                            Dim sValC As String = ""
                                                            Try : sTagC = CStr(oAtt.TagString) : Catch : End Try
                                                            Try : sValC = CStr(oAtt.TextString) : Catch : End Try
                                                            sbDbTags.Append(sTagC & "='" & sValC & "'; ")
                                                            If String.Compare(sTagC, "DRAWING_DESCRIPTION_2", True) = 0 _
                                                               OrElse (sAcadDesc = "" AndAlso (sTagC.ToUpper().Contains("DESCRIPTION") OrElse sTagC.ToUpper().Contains("DRAWING"))) Then
                                                                sAcadDesc = Trim(sValC)
                                                            End If
                                                        Next
                                                    End If
                                                End If
                                            Next
                                            If sAcadDesc <> "" Then Exit For
                                        Next
                                    End If
                                End If
                            End If
                        Catch exDb As Exception
                            Try : System.IO.File.AppendAllText(sLogPath, "DWGLIST-AUTOCAD-COM-FAIL: " & System.IO.Path.GetFileName(sDLCheck) & " " & exDb.Message & vbCrLf) : Catch : End Try
                        Finally
                            If bAcadOpened2 AndAlso oAcadDwg2 IsNot Nothing Then
                                Try : oAcadDwg2.Close(False) : Catch : End Try
                            End If
                        End Try
                        If sbDbTags.Length > 0 Then
                            Try : System.IO.File.AppendAllText(sLogPath, "DWGLIST-AUTOCAD-COM-TAGS: " & System.IO.Path.GetFileName(sDLCheck) & " : " & sbDbTags.ToString() & vbCrLf) : Catch : End Try
                        Else
                            Try : System.IO.File.AppendAllText(sLogPath, "DWGLIST-AUTOCAD-COM-TAGS: " & System.IO.Path.GetFileName(sDLCheck) & " : (no attributes via ContainingDWGDocument)" & vbCrLf) : Catch : End Try
                        End If
                    End If
                Catch
                End Try
                oAcadDwgDescs(sDLCheck) = sAcadDesc
                Try : System.IO.File.AppendAllText(sLogPath, "DWGLIST-AUTOCAD: " & System.IO.Path.GetFileName(sDLCheck) & If(sAcadDesc <> "", " [desc=" & sAcadDesc & "]", " [no desc found]") & vbCrLf) : Catch : End Try
            Catch
            End Try
        Next

        ' Scan each drawing for its referenced models
        Dim oDLDoc As Document
        Dim bDLOpenedHere As Boolean
        ' v2.2.21: late-bound descriptor/doc objects (no FileDescriptor cast)
        Dim oDLDD As Object
        Dim oDLRefDoc As Object
        Dim iDLLt As Integer
        Dim bDLScanOK As Boolean
        Dim sDLRef As String
        Dim sDLExt As String
        Dim oDLRefs As System.Collections.Generic.List(Of String)
        Dim oDLRefSeen As System.Collections.Generic.HashSet(Of String)
        ' Disable iLogic event-driven rules during document opens in the scan loop.
        ' Event rules (e.g. "Working Drawing Stamp") fire DURING Documents.Open and
        ' produce a blocking modal that sits behind other windows.
        Try : ThisApplication.iLogicVb.EventRuleManager.DisableEventRules = True : Catch : End Try
        ThisApplication.SilentOperation = True
        For Each sDLFile In oDwgFiles
            ' Skip native AutoCAD DWG files — cannot open via Inventor API.
            If oAcadDwgs.Contains(sDLFile) Then Continue For
            oDLDoc = Nothing
            bDLOpenedHere = False
            Try
                oDLDoc = ThisApplication.Documents.ItemByName(sDLFile)
            Catch
            End Try
            If oDLDoc Is Nothing Then
                Try
                    oDLDoc = ThisApplication.Documents.Open(sDLFile, False)
                    bDLOpenedHere = True
                Catch exDLOpen As Exception
                    Try : System.IO.File.AppendAllText(sLogPath, "DWGLIST-OPEN-FAIL: " & System.IO.Path.GetFileName(sDLFile) & " — " & exDLOpen.Message & vbCrLf) : Catch : End Try
                End Try
            End If
            If oDLDoc Is Nothing Then Continue For
            oDLRefs = New System.Collections.Generic.List(Of String)()
            oDLRefSeen = New System.Collections.Generic.HashSet(Of String)(StringComparer.OrdinalIgnoreCase)
            ' v2.2.21: ReferencedDocumentDescriptors (includes DART SHUT refs);
            ' strip any <...> tag; fall back to ReferencedDocuments on exception.
            bDLScanOK = False
            Try
                For Each oDLDD In oDLDoc.ReferencedDocumentDescriptors
                    sDLRef = ""
                    sDLExt = ""
                    Try
                        sDLRef = CStr(oDLDD.FullDocumentName)
                    Catch
                    End Try
                    If sDLRef Is Nothing Then
                        sDLRef = ""
                    End If
                    iDLLt = sDLRef.IndexOf("<")
                    If iDLLt >= 0 Then
                        sDLRef = sDLRef.Substring(0, iDLLt).Trim()
                    End If
                    If sDLRef = "" Then Continue For
                    Try
                        sDLExt = System.IO.Path.GetExtension(sDLRef).ToUpper()
                    Catch
                    End Try
                    If (sDLExt = ".IAM" OrElse sDLExt = ".IPT") AndAlso Not oDLRefSeen.Contains(sDLRef) Then
                        oDLRefSeen.Add(sDLRef)
                        oDLRefs.Add(sDLRef)
                    End If
                Next
                bDLScanOK = True
            Catch exDLDesc As Exception
                Try : System.IO.File.AppendAllText(sLogPath, "DWGLIST-REF-FALLBACK: " & System.IO.Path.GetFileName(sDLFile) & " — descriptors failed (" & exDLDesc.Message & "), using ReferencedDocuments" & vbCrLf) : Catch : End Try
            End Try
            If Not bDLScanOK Then
                Try
                    For Each oDLRefDoc In oDLDoc.ReferencedDocuments
                        sDLRef = ""
                        sDLExt = ""
                        Try
                            sDLRef = CStr(oDLRefDoc.FullDocumentName)
                        Catch
                        End Try
                        If sDLRef Is Nothing Then
                            sDLRef = ""
                        End If
                        iDLLt = sDLRef.IndexOf("<")
                        If iDLLt >= 0 Then
                            sDLRef = sDLRef.Substring(0, iDLLt).Trim()
                        End If
                        If sDLRef = "" Then Continue For
                        Try
                            sDLExt = System.IO.Path.GetExtension(sDLRef).ToUpper()
                        Catch
                        End Try
                        If (sDLExt = ".IAM" OrElse sDLExt = ".IPT") AndAlso Not oDLRefSeen.Contains(sDLRef) Then
                            oDLRefSeen.Add(sDLRef)
                            oDLRefs.Add(sDLRef)
                        End If
                    Next
                Catch exDLRef As Exception
                    Try : System.IO.File.AppendAllText(sLogPath, "DWGLIST-REF-FAIL: " & System.IO.Path.GetFileName(sDLFile) & " — " & exDLRef.Message & vbCrLf) : Catch : End Try
                End Try
            End If
            If bDLOpenedHere Then
                Try : oDLDoc.Close(True) : Catch : End Try
            End If
            If oDLRefs.Count > 0 Then
                oDwgList.Add(sDLFile)
                oDwgModels(sDLFile) = oDLRefs
                Try : System.IO.File.AppendAllText(sLogPath, "DWGLIST: " & System.IO.Path.GetFileName(sDLFile) & " (" & oDLRefs.Count & " model(s))" & vbCrLf) : Catch : End Try
            End If
        Next
        ' Restore event rules after scan loop — the form dialog shown next must not suppress them.
        Try : ThisApplication.iLogicVb.EventRuleManager.DisableEventRules = False : Catch : End Try

        ' v2.2.23: same Traverse layout, but the new-name master is keyed by
        ' old-model basename (case-insensitive), not full path.  Always shown
        ' when started from a drawing, even if some/all scans failed.
        If True Then
            ThisApplication.SilentOperation = bOrigSilent
            Dim iDMFormW As Integer = 680
            Dim iDMPanelLeft As Integer = 10
            Dim iDMPanelW As Integer = 648
            Dim iDMOldLeft As Integer = 6
            Dim iDMOldW As Integer = 268
            Dim iDMNewLeft As Integer = 300
            Dim iDMNewW As Integer = 336
            Dim oDLForm As New System.Windows.Forms.Form()
            oDLForm.Text = "Drawing Model Renames — Models and New Names"
            oDLForm.FormBorderStyle = System.Windows.Forms.FormBorderStyle.FixedDialog
            oDLForm.StartPosition = System.Windows.Forms.FormStartPosition.CenterScreen
            oDLForm.MaximizeBox = False
            oDLForm.MinimizeBox = False
            oDLForm.Width = iDMFormW
            oDLForm.Height = 640
            Dim oDLHint As New System.Windows.Forms.Label()
            oDLHint.Text = "Set NEW model names below — applied FIRST. String rules will NOT rename any model listed here."
            oDLHint.Left = 10
            oDLHint.Top = 8
            oDLHint.Width = iDMFormW - 20
            oDLHint.Height = 18
            oDLForm.Controls.Add(oDLHint)
            Dim oDLOldHdr As New System.Windows.Forms.Label()
            oDLOldHdr.Text = "CURRENT model name (read-only)"
            oDLOldHdr.Left = iDMPanelLeft + 1 + iDMOldLeft
            oDLOldHdr.Top = 30
            oDLOldHdr.Width = iDMOldW
            oDLForm.Controls.Add(oDLOldHdr)
            Dim oDLNewHdr As New System.Windows.Forms.Label()
            oDLNewHdr.Text = "NEW model name (editable)"
            oDLNewHdr.Left = iDMPanelLeft + 1 + iDMNewLeft
            oDLNewHdr.Top = 30
            oDLNewHdr.Width = iDMNewW
            oDLForm.Controls.Add(oDLNewHdr)
            Dim oDLPanel As New System.Windows.Forms.Panel()
            oDLPanel.Left = iDMPanelLeft
            oDLPanel.Top = 50
            oDLPanel.Width = iDMPanelW
            oDLPanel.Height = 490
            oDLPanel.AutoScroll = True
            oDLPanel.BorderStyle = System.Windows.Forms.BorderStyle.FixedSingle
            oDLForm.Controls.Add(oDLPanel)

            ' v2.2.23: basename (file name) -> the one editable master TextBox
            Dim oDLMasterByBase As New System.Collections.Generic.Dictionary(Of String, System.Windows.Forms.TextBox)( _
                StringComparer.OrdinalIgnoreCase)
            Dim oDLPrefill As New System.Collections.Generic.Dictionary(Of String, String)( _
                StringComparer.OrdinalIgnoreCase)
            Dim oDMIncludeMap As New System.Collections.Generic.Dictionary(Of String, System.Windows.Forms.CheckBox)( _
                StringComparer.OrdinalIgnoreCase)
            ' Per-drawing "Match model states?" checkboxes — keyed by full drawing path
            Dim oStateCheckMap As New System.Collections.Generic.Dictionary(Of String, System.Windows.Forms.CheckBox)( _
                StringComparer.OrdinalIgnoreCase)

            Dim iDLY As Integer = 6
            Dim iDMDrawingNum As Integer = 0
            Dim iDMPanelH As Integer = 0
            Dim iDMMY As Integer = 0
            Dim iDMTxtLeft As Integer = 0
            Dim iDMTxtW As Integer = 0
            If oDwgList.Count = 0 Then
                Dim oDLNone As New System.Windows.Forms.Label()
                oDLNone.Text = "No model refs were found in the drawings in this folder.  OK continues with the automatic names; Cancel exits."
                oDLNone.Left = 4
                oDLNone.Top = iDLY
                oDLNone.Width = 620
                oDLNone.Height = 40
                oDLPanel.Controls.Add(oDLNone)
                iDLY = iDLY + 44
                Try : System.IO.File.AppendAllText(sLogPath, "DWGLIST: no model refs found in any drawing" & vbCrLf) : Catch : End Try
            End If
            Dim sDLDwg As String
            Dim sDLModel As String
            Dim sDLNewFull As String
            Dim sDLPre As String
            Dim sDLBaseName As String
            Dim oDMNumLbl As System.Windows.Forms.Label
            Dim oDMInclChk As System.Windows.Forms.CheckBox
            Dim oDMDwgLbl As System.Windows.Forms.Label
            Dim oDMBorder As System.Windows.Forms.Panel
            Dim oDLOld As System.Windows.Forms.Label
            Dim oDMArrLbl As System.Windows.Forms.Label
            Dim oDLBox As System.Windows.Forms.TextBox
            Dim oDMLockedBox As System.Windows.Forms.TextBox
            For Each sDLDwg In oDwgList
                iDMDrawingNum = iDMDrawingNum + 1
                oDMNumLbl = New System.Windows.Forms.Label()
                oDMNumLbl.Text = iDMDrawingNum.ToString() & "."
                oDMNumLbl.Left = 4
                oDMNumLbl.Top = iDLY
                oDMNumLbl.Width = 22
                oDMNumLbl.Height = 20
                oDLPanel.Controls.Add(oDMNumLbl)
                oDMInclChk = New System.Windows.Forms.CheckBox()
                oDMInclChk.Left = 26
                oDMInclChk.Top = iDLY - 1
                oDMInclChk.Width = 18
                oDMInclChk.Height = 20
                oDMInclChk.Checked = True
                oDMInclChk.Tag = sDLDwg
                oDLPanel.Controls.Add(oDMInclChk)
                oDMIncludeMap(sDLDwg) = oDMInclChk
                oDMDwgLbl = New System.Windows.Forms.Label()
                oDMDwgLbl.Text = System.IO.Path.GetFileName(sDLDwg)
                oDMDwgLbl.Left = 46
                oDMDwgLbl.Top = iDLY
                oDMDwgLbl.Width = 390
                oDMDwgLbl.Height = 20
                oDLPanel.Controls.Add(oDMDwgLbl)
                ' "Match model states?" — re-asserts named DrawingView model states after relink.
                ' Needed when a drawing has views pointing at named model states (e.g. Weldment).
                Dim oDMStateChk As New System.Windows.Forms.CheckBox()
                oDMStateChk.Text = "Match model states?"
                oDMStateChk.Left = 440
                oDMStateChk.Top = iDLY - 1
                oDMStateChk.Width = 190
                oDMStateChk.Height = 20
                oDMStateChk.Checked = True
                oDMStateChk.Tag = sDLDwg
                oDLPanel.Controls.Add(oDMStateChk)
                oStateCheckMap(sDLDwg) = oDMStateChk
                iDLY = iDLY + 24
                iDMPanelH = oDwgModels(sDLDwg).Count * 26 + 6
                If iDMPanelH < 32 Then iDMPanelH = 32
                oDMBorder = New System.Windows.Forms.Panel()
                oDMBorder.Left = iDMOldLeft
                oDMBorder.Top = iDLY
                oDMBorder.Width = iDMPanelW - iDMOldLeft * 2 - 4
                oDMBorder.Height = iDMPanelH
                oDMBorder.BorderStyle = System.Windows.Forms.BorderStyle.FixedSingle
                oDLPanel.Controls.Add(oDMBorder)
                iDMMY = 3
                For Each sDLModel In oDwgModels(sDLDwg)
                    oDLOld = New System.Windows.Forms.Label()
                    oDLOld.Text = System.IO.Path.GetFileName(sDLModel)
                    oDLOld.Left = 2
                    oDLOld.Top = iDMMY
                    oDLOld.Width = iDMOldW - 2
                    oDLOld.Height = 20
                    oDMBorder.Controls.Add(oDLOld)
                    oDMArrLbl = New System.Windows.Forms.Label()
                    oDMArrLbl.Text = "->"
                    oDMArrLbl.Left = iDMOldW + 4
                    oDMArrLbl.Top = iDMMY
                    oDMArrLbl.Width = 20
                    oDMArrLbl.Height = 20
                    oDMBorder.Controls.Add(oDMArrLbl)
                    iDMTxtLeft = iDMOldW + 26
                    iDMTxtW = oDMBorder.Width - iDMTxtLeft - 4
                    sDLBaseName = System.IO.Path.GetFileName(sDLModel)
                    If oDLMasterByBase.ContainsKey(sDLBaseName) Then
                        ' Later appearance of the same basename — read-only mirror
                        oDMLockedBox = New System.Windows.Forms.TextBox()
                        oDMLockedBox.Left = iDMTxtLeft
                        oDMLockedBox.Top = iDMMY
                        oDMLockedBox.Width = iDMTxtW
                        oDMLockedBox.ReadOnly = True
                        oDMLockedBox.Text = oDLMasterByBase(sDLBaseName).Text
                        If Not oDLMasterByBase(sDLBaseName).Enabled Then
                            oDMLockedBox.Enabled = False
                        End If
                        WireDMTextSync(oDLMasterByBase(sDLBaseName), oDMLockedBox)
                        oDMBorder.Controls.Add(oDMLockedBox)
                    Else
                        ' First appearance is the master (prefilled computed new name)
                        sDLNewFull = ComputeNewName(sDLModel, sOldProjectRoot, sNewPrefix, sTargetFolder)
                        oDLBox = New System.Windows.Forms.TextBox()
                        oDLBox.Left = iDMTxtLeft
                        oDLBox.Top = iDMMY
                        oDLBox.Width = iDMTxtW
                        If sDLNewFull = "" Then
                            ' not copied (Content Center or already in target) — locked master
                            sDLPre = System.IO.Path.GetFileNameWithoutExtension(sDLModel)
                            oDLBox.Text = sDLPre
                            oDLBox.ReadOnly = True
                            oDLBox.Enabled = False
                        Else
                            sDLPre = System.IO.Path.GetFileNameWithoutExtension(ApplyStringRules(sDLNewFull, oStringRules))
                            oDLBox.Text = sDLPre
                            oDLBox.Tag = sDLModel
                        End If
                        oDLPrefill(sDLBaseName) = sDLPre
                        oDLMasterByBase(sDLBaseName) = oDLBox
                        oDMBorder.Controls.Add(oDLBox)
                    End If
                    iDMMY = iDMMY + 26
                Next
                iDLY = iDLY + iDMPanelH + 8
            Next

            ' v2.2.27: AutoCAD DWGs appear inline in the numbered list — same layout as
            ' Inventor drawings but with the checkbox disabled/unchecked and a bordered
            ' "Autocad Created Drawing – not included in This Clean Sweep" note below.
            ' The description from DRAWING_DESCRIPTION_2 is shown to the right of the filename.
            If oAcadDwgs.Count > 0 Then
                Dim oAcadSorted As New System.Collections.Generic.List(Of String)(oAcadDwgs)
                oAcadSorted.Sort(StringComparer.OrdinalIgnoreCase)
                For Each sAcadEntry As String In oAcadSorted
                    iDMDrawingNum = iDMDrawingNum + 1

                    ' Number label
                    Dim oAcadNumLbl As New System.Windows.Forms.Label()
                    oAcadNumLbl.Text = iDMDrawingNum.ToString() & "."
                    oAcadNumLbl.Left = 4 : oAcadNumLbl.Top = iDLY
                    oAcadNumLbl.Width = 22 : oAcadNumLbl.Height = 20
                    oDLPanel.Controls.Add(oAcadNumLbl)

                    ' Include checkbox — disabled + unchecked (AutoCAD excluded from sweep)
                    Dim oAcadChk As New System.Windows.Forms.CheckBox()
                    oAcadChk.Left = 26 : oAcadChk.Top = iDLY - 1
                    oAcadChk.Width = 18 : oAcadChk.Height = 20
                    oAcadChk.Checked = False
                    oAcadChk.Enabled = False
                    oDLPanel.Controls.Add(oAcadChk)

                    ' Filename label — with description to the right if available
                    Dim sAcadDescInline As String = ""
                    If oAcadDwgDescs.ContainsKey(sAcadEntry) Then sAcadDescInline = Trim(oAcadDwgDescs(sAcadEntry))
                    Dim oAcadFileLbl As New System.Windows.Forms.Label()
                    Dim sAcadLblText As String = System.IO.Path.GetFileName(sAcadEntry)
                    If sAcadDescInline <> "" Then sAcadLblText = sAcadLblText & "   " & sAcadDescInline
                    oAcadFileLbl.Text = sAcadLblText
                    oAcadFileLbl.Left = 46 : oAcadFileLbl.Top = iDLY
                    oAcadFileLbl.Width = 580 : oAcadFileLbl.Height = 20
                    oDLPanel.Controls.Add(oAcadFileLbl)
                    iDLY = iDLY + 24

                    ' Bordered note panel — matches the model-list border on regular drawings
                    Dim oAcadBorder As New System.Windows.Forms.Panel()
                    oAcadBorder.Left = iDMOldLeft : oAcadBorder.Top = iDLY
                    oAcadBorder.Width = iDMPanelW - iDMOldLeft * 2 - 4 : oAcadBorder.Height = 22
                    oAcadBorder.BorderStyle = System.Windows.Forms.BorderStyle.FixedSingle
                    Dim oAcadNoteLbl As New System.Windows.Forms.Label()
                    oAcadNoteLbl.Text = "Autocad Created Drawing - not included in This Clean Sweep"
                    oAcadNoteLbl.Left = 4 : oAcadNoteLbl.Top = 2
                    oAcadNoteLbl.Width = oAcadBorder.Width - 8 : oAcadNoteLbl.Height = 18
                    oAcadBorder.Controls.Add(oAcadNoteLbl)
                    oDLPanel.Controls.Add(oAcadBorder)
                    iDLY = iDLY + 30
                Next
            End If

            Dim oDMIncludeAll As New System.Windows.Forms.CheckBox()
            oDMIncludeAll.Text = "Include ALL drawings"
            oDMIncludeAll.Left = 10
            oDMIncludeAll.Top = 548
            oDMIncludeAll.Width = 300
            oDMIncludeAll.Checked = True
            oDLForm.Controls.Add(oDMIncludeAll)
            WireDMIncludeAll(oDMIncludeAll, oDMIncludeMap)

            Dim oDLOk As New System.Windows.Forms.Button()
            oDLOk.Text = "OK"
            oDLOk.Left = 476
            oDLOk.Top = 576
            oDLOk.Width = 80
            oDLOk.DialogResult = System.Windows.Forms.DialogResult.OK
            oDLForm.Controls.Add(oDLOk)
            Dim oDLCancel As New System.Windows.Forms.Button()
            oDLCancel.Text = "Cancel"
            oDLCancel.Left = 568
            oDLCancel.Top = 576
            oDLCancel.Width = 80
            oDLCancel.DialogResult = System.Windows.Forms.DialogResult.Cancel
            oDLForm.Controls.Add(oDLCancel)
            oDLForm.AcceptButton = oDLOk
            oDLForm.CancelButton = oDLCancel
            Dim oDLRes As System.Windows.Forms.DialogResult = oDLForm.ShowDialog()
            If oDLRes <> System.Windows.Forms.DialogResult.OK Then
                Try : oDLForm.Dispose() : Catch : End Try
                ThisApplication.SilentOperation = bOrigSilent
                If bEntryDocOpenedHere AndAlso oEntryDoc IsNot Nothing Then  ' FIX A
                    Try : oEntryDoc.Close(True) : Catch : End Try
                End If
                MessageBox.Show("Cancelled — no changes made.", "Super Clean Sweeper")
                Exit Sub
            End If

            ' Remove unchecked drawings from oDwgList (relink skips them).
            ' Included models are grouped by basename so the master text applies
            ' to every full path of that basename, even if the master row sits
            ' on a drawing the user then excluded.
            Dim oDMKeepList As New System.Collections.Generic.List(Of String)()
            Dim oDMBasePaths As New System.Collections.Generic.Dictionary(Of String, System.Collections.Generic.List(Of String))( _
                StringComparer.OrdinalIgnoreCase)
            Dim oDMPathList As System.Collections.Generic.List(Of String)
            Dim sDMBaseKey As String
            Dim bDMPathSeen As Boolean
            Dim sDMSeenPath As String
            For Each sDLDwg In oDwgList
                If oDMIncludeMap.ContainsKey(sDLDwg) AndAlso oDMIncludeMap(sDLDwg).Checked Then
                    oDMKeepList.Add(sDLDwg)
                    For Each sDLModel In oDwgModels(sDLDwg)
                        sDMBaseKey = System.IO.Path.GetFileName(sDLModel)
                        If Not oDMBasePaths.ContainsKey(sDMBaseKey) Then
                            oDMBasePaths(sDMBaseKey) = New System.Collections.Generic.List(Of String)()
                        End If
                        oDMPathList = oDMBasePaths(sDMBaseKey)
                        bDMPathSeen = False
                        For Each sDMSeenPath In oDMPathList
                            If String.Equals(sDMSeenPath, sDLModel, StringComparison.OrdinalIgnoreCase) Then
                                bDMPathSeen = True
                                Exit For
                            End If
                        Next
                        If Not bDMPathSeen Then
                            oDMPathList.Add(sDLModel)
                        End If
                    Next
                Else
                    Try : System.IO.File.AppendAllText(sLogPath, "DWG-EXCLUDED: " & System.IO.Path.GetFileName(sDLDwg) & vbCrLf) : Catch : End Try
                End If
            Next
            oDwgList.Clear()
            For Each sDLDwg In oDMKeepList
                oDwgList.Add(sDLDwg)
            Next

            ' On OK only the master textbox is read.  Locked follower boxes are ignored.
            Dim oDLKV As System.Collections.Generic.KeyValuePair(Of String, System.Windows.Forms.TextBox)
            Dim sDLTyped As String
            Dim sDLModelExt As String
            Dim sDMMasterBase As String
            For Each oDLKV In oDLMasterByBase
                sDMMasterBase = oDLKV.Key
                If oDLKV.Value.ReadOnly Then Continue For
                If Not oDMBasePaths.ContainsKey(sDMMasterBase) Then Continue For
                oDMPathList = oDMBasePaths(sDMMasterBase)
                If oDMPathList.Count = 0 Then Continue For
                sDLTyped = oDLKV.Value.Text.Trim()
                sDLModelExt = System.IO.Path.GetExtension(oDMPathList(0))
                If sDLTyped.ToUpper().EndsWith(sDLModelExt.ToUpper()) AndAlso sDLTyped.Length > sDLModelExt.Length Then
                    sDLTyped = sDLTyped.Substring(0, sDLTyped.Length - sDLModelExt.Length)
                End If
                If sDLTyped = "" Then Continue For
                If oDLPrefill.ContainsKey(sDMMasterBase) AndAlso String.Equals(sDLTyped, oDLPrefill(sDMMasterBase), StringComparison.Ordinal) Then Continue For
                If sDLTyped.IndexOfAny(System.IO.Path.GetInvalidFileNameChars()) >= 0 Then
                    Try : System.IO.File.AppendAllText(sLogPath, "DWG-NAME-INVALID: " & sDMMasterBase & " -> " & sDLTyped & " (ignored)" & vbCrLf) : Catch : End Try
                    Continue For
                End If
                For Each sDLModel In oDMPathList
                    oNameOverrides(sDLModel) = sDLTyped
                    Try : System.IO.File.AppendAllText(sLogPath, "DWG-NAME: " & System.IO.Path.GetFileName(sDLModel) & " -> " & sDLTyped & sDLModelExt & vbCrLf) : Catch : End Try
                Next
            Next
            ' Build oDrawingStateMatch from the per-drawing "Match model states?" checkboxes
            For Each sDLDwg In oDwgList
                Dim bStateOn As Boolean = True   ' default on if checkbox missing
                If oStateCheckMap.ContainsKey(sDLDwg) Then bStateOn = oStateCheckMap(sDLDwg).Checked
                oDrawingStateMatch(sDLDwg) = bStateOn
                Try : System.IO.File.AppendAllText(sLogPath, "DWG-STATE-MATCH: " & System.IO.Path.GetFileName(sDLDwg) & " = " & bStateOn.ToString() & vbCrLf) : Catch : End Try
            Next
            Try : oDLForm.Dispose() : Catch : End Try
            Try : System.IO.File.AppendAllText(sLogPath, "DWGLIST: " & oDwgList.Count & " drawing(s), " & oNameOverrides.Count & " name override(s)." & vbCrLf) : Catch : End Try

            ' v2.2.25: Restrict oDwgModels to included drawings + entry drawing only.
            ' The initial scan populated it from ALL drawings; orphan processing must only
            ' run against drawings the user chose to include, otherwise excluded drawings
            ' flood the orphan loop with models the user didn't ask to process.
            Dim oIncludedForOrphans As New System.Collections.Generic.HashSet(Of String)( _
                oDwgList, StringComparer.OrdinalIgnoreCase)
            If sDwgEntryPath <> "" Then oIncludedForOrphans.Add(sDwgEntryPath)
            Dim oOrphanDwgRemove As New System.Collections.Generic.List(Of String)()
            For Each sDMKey As String In oDwgModels.Keys
                If Not oIncludedForOrphans.Contains(sDMKey) Then oOrphanDwgRemove.Add(sDMKey)
            Next
            For Each sDMKey As String In oOrphanDwgRemove
                oDwgModels.Remove(sDMKey)
            Next
            Try : System.IO.File.AppendAllText(sLogPath, "DWGMODELS: orphan scan restricted to " & oDwgModels.Count & " drawing(s) after exclusions." & vbCrLf) : Catch : End Try
        End If
        ThisApplication.SilentOperation = True
    End If

    ' ── Shared result variables — visible in both bRelinkOnly and full paths ─
    Dim oRenameMap As New System.Collections.Generic.Dictionary(Of String, String)( _
        StringComparer.OrdinalIgnoreCase)
    Dim oActualMap As New System.Collections.Generic.Dictionary(Of String, String)( _
        StringComparer.OrdinalIgnoreCase)
    Dim iSaved      As Integer = 0
    Dim iSkipped    As Integer = 0
    Dim iSaveFailed As Integer = 0
    Dim iRefFixed   As Integer = 0
    Dim iRefFailed  As Integer = 0
    Dim iNoProvenance As Integer = 0
    Dim oProvRebuildOpened As New System.Collections.Generic.List(Of Document)()
    Dim sKeepOpenGA As String = ""

    ' ── 5. PHASE 1 — Build rename map ────────────────────────────────────────
    If Not bRelinkOnly Then
    Try : System.IO.File.AppendAllText(sLogPath, vbCrLf & "=== PHASE 1: RENAME MAP ===" & vbCrLf) : Catch : End Try

    Dim oSeen As New System.Collections.Generic.HashSet(Of String)( _
        StringComparer.OrdinalIgnoreCase)

    ' FIX 4/5: oMappedTargets = O(1) HashSet mirror of oRenameMap.Values
    '          oWalkOpened    = documents opened by WalkTree, closed before Phase 2
    Dim oMappedTargets As New System.Collections.Generic.HashSet(Of String)( _
        StringComparer.OrdinalIgnoreCase)
    Dim oWalkOpened As New System.Collections.Generic.List(Of Document)()
    ' v2.2.15: sources whose target is an existing file being reused (Phase 2 skips SaveAs)
    Dim oReuseKeys As New System.Collections.Generic.HashSet(Of String)( _
        StringComparer.OrdinalIgnoreCase)
    ' v2.2.17: cache of CS_SourcePath reads (target path -> CS_SourcePath)
    Dim oSourcePathCache As New System.Collections.Generic.Dictionary(Of String, String)( _
        StringComparer.OrdinalIgnoreCase)

    Try
        WalkTree(oAsmDoc, sOldProjectRoot, sNewPrefix, sTargetFolder, _
                 oRenameMap, oSeen, sLogPath, oMappedTargets, oWalkOpened, _
                 oStringRules, oReuseKeys, oSourcePathCache, oNameOverrides)
    Catch exWalk As Exception
        ThisApplication.SilentOperation = bOrigSilent
        If bEntryDocOpenedHere AndAlso oEntryDoc IsNot Nothing Then  ' FIX A
            Try : oEntryDoc.Close(True) : Catch : End Try
        End If
        MessageBox.Show("Phase 1 walk failed: " & exWalk.Message, "Super Clean Sweeper")
        Exit Sub
    End Try

    ' Add the top assembly itself
    ' If it's already in the target folder (same-prefix rerun), skip it.
    ' Otherwise map it.
    Dim sTopNewFull2 As String = ComputeNewName(sTopFull, sOldProjectRoot, sNewPrefix, sTargetFolder)
    ' v2.2.19: Drawing List name replaces the automatic new base name
    Dim bTopOverride As Boolean = False
    If sTopNewFull2 <> "" AndAlso oNameOverrides.ContainsKey(sTopFull) Then
        sTopNewFull2 = System.IO.Path.Combine(System.IO.Path.GetDirectoryName(sTopNewFull2), _
            oNameOverrides(sTopFull) & System.IO.Path.GetExtension(sTopFull))
        bTopOverride = True
    End If
    If sTopNewFull2 <> "" Then
        If Not oRenameMap.ContainsKey(sTopFull) Then
            ' v2.2.15: apply string rules, then reuse / suffix per provenance
            Dim sTopRuled As String = sTopNewFull2
            If Not bTopOverride Then sTopRuled = ApplyStringRules(sTopNewFull2, oStringRules)
            Dim bTopRuleChanged As Boolean = Not String.Equals(sTopRuled, sTopNewFull2, StringComparison.Ordinal)
            Dim bTopReused As Boolean = False
            Dim sTopTest As String = ResolveTarget(sTopFull, sTopRuled, bTopRuleChanged, oMappedTargets, sLogPath, bTopReused, oSourcePathCache)
            ' v2.2.17: "" means the suffix range was exhausted — skip mapping the top GA
            If sTopTest <> "" Then
                If bTopReused Then oReuseKeys.Add(sTopFull)
                oRenameMap(sTopFull) = sTopTest
                oMappedTargets.Add(sTopTest)
                Try : System.IO.File.AppendAllText(sLogPath, _
                    "MAP (TOP): " & System.IO.Path.GetFileName(sTopFull) & _
                    "  ->  " & System.IO.Path.GetFileName(sTopTest) & vbCrLf) : Catch : End Try
            End If
        End If
    End If

    Try : System.IO.File.AppendAllText(sLogPath, _
        "Phase 1 complete: " & oRenameMap.Count & " file(s) in map." & vbCrLf) : Catch : End Try

    ' FIX 4: Close all documents opened by WalkTree before Phase 2 starts.
    ' Phase 2 re-opens what it needs with bOpenedHere2 = True for proper lifecycle.
    For Each oWD As Document In oWalkOpened
        Try : oWD.Close(True) : Catch : End Try
    Next
    oWalkOpened.Clear()

    ' v2.2.5: on a rerun Phase 1 can find 0 files (everything is already in the
    ' target folder).  Rebuild old->new pairs from CS_SourcePath on every .iam/.ipt
    ' in the target folder so Phase 4 can still run.  The pairs are merged into
    ' oActualMap as soon as it is created (inside the outer Try).
    Dim oRecoveredMap As New System.Collections.Generic.Dictionary(Of String, String)( _
        StringComparer.OrdinalIgnoreCase)
    If oRenameMap.Count = 0 Then
        Try : System.IO.File.AppendAllText(sLogPath, vbCrLf & "=== RERUN: PROVENANCE RECOVERY (Phase 1 found 0 files) ===" & vbCrLf) : Catch : End Try
        Dim sRecFile As String
        Dim sRecExt As String
        Dim sRecSource As String
        Dim oRecDoc As Document
        Dim bRecOpened As Boolean
        Dim aRecFiles() As String = New String() {}
        Try
            aRecFiles = System.IO.Directory.GetFiles(sTargetFolder, "*.*", System.IO.SearchOption.TopDirectoryOnly)
        Catch exRecDir As Exception
            Try : System.IO.File.AppendAllText(sLogPath, "REC-DIR-FAIL: " & exRecDir.Message & vbCrLf) : Catch : End Try
        End Try
        For Each sRecFile In aRecFiles
            sRecExt = System.IO.Path.GetExtension(sRecFile).ToUpper()
            If sRecExt <> ".IAM" AndAlso sRecExt <> ".IPT" Then Continue For
            sRecSource = ""
            oRecDoc = Nothing
            bRecOpened = False
            Try
                oRecDoc = ThisApplication.Documents.ItemByName(sRecFile)
            Catch
            End Try
            If oRecDoc Is Nothing Then
                Try
                    ThisApplication.SilentOperation = True
                    oRecDoc = ThisApplication.Documents.Open(sRecFile, False)
                    bRecOpened = True
                Catch exRecOpen As Exception
                    Try : System.IO.File.AppendAllText(sLogPath, "REC-OPEN-FAIL: " & System.IO.Path.GetFileName(sRecFile) & " — " & exRecOpen.Message & vbCrLf) : Catch : End Try
                End Try
            End If
            If oRecDoc IsNot Nothing Then
                Try
                    sRecSource = CStr(oRecDoc.PropertySets("Inventor User Defined Properties").Item("CS_SourcePath").Value)
                Catch
                End Try
                If bRecOpened Then
                    Try : oRecDoc.Close(True) : Catch : End Try
                End If
            End If
            If sRecSource <> "" AndAlso String.Compare(sRecSource, sRecFile, True) <> 0 Then
                If Not oRecoveredMap.ContainsKey(sRecSource) Then
                    oRecoveredMap(sRecSource) = sRecFile
                    Try : System.IO.File.AppendAllText(sLogPath, "REC-PROV: " & System.IO.Path.GetFileName(sRecSource) & " -> " & System.IO.Path.GetFileName(sRecFile) & vbCrLf) : Catch : End Try
                End If
            End If
        Next
        Try : System.IO.File.AppendAllText(sLogPath, "Provenance recovery complete: " & oRecoveredMap.Count & " entr(ies) recovered." & vbCrLf) : Catch : End Try
    End If

    If oRenameMap.Count = 0 AndAlso oRecoveredMap.Count = 0 Then
        ThisApplication.SilentOperation = bOrigSilent
        If bEntryDocOpenedHere AndAlso oEntryDoc IsNot Nothing Then  ' FIX A
            Try : oEntryDoc.Close(True) : Catch : End Try
        End If
        MessageBox.Show("No files found under project root '" & sOldProjectRoot & "'." & vbCrLf & _
            "Check the GA is open and the prefix matches its filename.", _
            "Super Clean Sweeper — Nothing to do")
        Exit Sub
    End If

    ' Confirm with user before making changes
    ThisApplication.SilentOperation = bOrigSilent
    Dim oConfirm As DialogResult = MessageBox.Show( _
        oRenameMap.Count & " file(s) will be processed:" & vbCrLf & _
        "• SaveAs (fresh GUID) → " & sTargetFolder & vbCrLf & _
        "• All files under: " & sOldProjectRoot & vbCrLf & _
        "• Provenance properties written (CS_SourcePath, CS_RootSource, CS_RunCount, etc.)" & vbCrLf & _
        "• Original files are NOT modified" & vbCrLf & vbCrLf & _
        "Proceed?", _
        "Super Clean Sweeper — Confirm", _
        MessageBoxButtons.YesNo, MessageBoxIcon.Question)
    If oConfirm <> DialogResult.Yes Then
        If bEntryDocOpenedHere AndAlso oEntryDoc IsNot Nothing Then  ' FIX A
            Try : oEntryDoc.Close(True) : Catch : End Try
        End If
        MessageBox.Show("Cancelled — no changes made.", "Super Clean Sweeper")
        Exit Sub
    End If
    ThisApplication.SilentOperation = True

    ' ── 6. PHASE 2 — SaveAs + Provenance ─────────────────────────────────────
    ' Process in deepest-first order: sort by OLD path length descending.
    ' (iSaved, iSkipped etc., oProvRebuildOpened, sKeepOpenGA declared above If Not bRelinkOnly)

    Try : System.IO.File.AppendAllText(sLogPath, vbCrLf & "=== PHASE 2: SAVEAS + PROVENANCE ===" & vbCrLf) : Catch : End Try
    Try  ' ← F1: outer Try/Finally — Finally restores SilentOperation

    Dim oMapKeys As New System.Collections.Generic.List(Of String)(oRenameMap.Keys)
    oMapKeys.Sort(Function(a2, b2) b2.Length.CompareTo(a2.Length))
    ' v2.2.10: process the top GA first so a hang on a later child still leaves the GA in the target folder.
    If oRenameMap.ContainsKey(sTopFull) Then
        oMapKeys.Remove(sTopFull)
        oMapKeys.Insert(0, sTopFull)
        Try : System.IO.File.AppendAllText(sLogPath, "PHASE 2 ORDER: top GA first — " & System.IO.Path.GetFileName(sTopFull) & vbCrLf) : Catch : End Try
    End If

    ' Track files actually placed on disk (Phase 3 uses this map)
    ' oActualMap declared before If Not bRelinkOnly block — re-init for a clean state
    oActualMap = New System.Collections.Generic.Dictionary(Of String, String)( _
        StringComparer.OrdinalIgnoreCase)
    ' v2.2.17: target files actually created (SaveAs / File.Copy) by THIS run.
    ' Phase 3 only opens and saves files in this set.
    Dim oCreatedThisRun As New System.Collections.Generic.HashSet(Of String)( _
        StringComparer.OrdinalIgnoreCase)

    ' v2.2.5: merge pairs recovered from provenance on a 0-file rerun.
    Dim sRecKey As String
    For Each sRecKey In oRecoveredMap.Keys
        oActualMap(sRecKey) = oRecoveredMap(sRecKey)
    Next

    ' ── PRE-POPULATE oActualMap from provenance of files already in target ────
    ' Files SaveAs'd in a PRIOR run are not in oRenameMap (ComputeNewName returns ""
    ' for them because they are already in sTargetFolder).  Read CS_SourcePath from
    ' matching files in the target folder to reconstruct the full old→new map so
    ' Phase 3 can repoint ALL stray references, not just the ones from this run.
    '
    ' FIX 2: .IAM and .IPT only — drawings (.IDW/.DWG) can't carry CS_SourcePath
    '        and opening partially-relinked drawings risks unresolved-ref dialogs.
    ' FIX 3: Only scan files whose basename matches an expected new filename,
    '        avoiding opening hundreds of prior-run files for nothing.
    Try : System.IO.File.AppendAllText(sLogPath, vbCrLf & "=== PRE-PHASE 2: REBUILD ACTUAL MAP FROM PROVENANCE ===" & vbCrLf) : Catch : End Try
    Dim iProvRebuild As Integer = 0

    ' FIX 3: Pre-compute set of expected new basenames from this run's rename map.
    Dim oExpectedNewBases As New System.Collections.Generic.HashSet(Of String)( _
        StringComparer.OrdinalIgnoreCase)
    For Each sExpVal As String In oRenameMap.Values
        oExpectedNewBases.Add(System.IO.Path.GetFileName(sExpVal))
    Next

    Try
        For Each sPRFile As String In System.IO.Directory.GetFiles(sTargetFolder, "*.*", _
                System.IO.SearchOption.TopDirectoryOnly)
            ' FIX 2: .IAM and .IPT only — drawings excluded
            Dim sPRExt As String = System.IO.Path.GetExtension(sPRFile).ToUpper()
            If sPRExt <> ".IAM" AndAlso sPRExt <> ".IPT" Then Continue For
            ' FIX 3: Skip files whose basename is not an expected new filename
            Dim sPRBase As String = System.IO.Path.GetFileName(sPRFile)
            If Not oExpectedNewBases.Contains(sPRBase) Then Continue For

            Dim sCSSource As String = ""
            Try
                Dim oPRDoc As Document = Nothing
                Try : oPRDoc = ThisApplication.Documents.ItemByName(sPRFile) : Catch : End Try
                If oPRDoc Is Nothing Then
                    Try
                        ThisApplication.SilentOperation = True
                        oPRDoc = ThisApplication.Documents.Open(sPRFile, False)
                        ' FIX 1: Track for explicit close in Finally
                        If oPRDoc IsNot Nothing Then oProvRebuildOpened.Add(oPRDoc)
                    Catch
                    End Try
                End If
                If oPRDoc IsNot Nothing Then
                    Try
                        sCSSource = oPRDoc.PropertySets( _
                            "Inventor User Defined Properties").Item("CS_SourcePath").Value
                    Catch : End Try
                    ' FIX 1: Don't close here — oProvRebuildOpened handles cleanup in Finally
                End If
            Catch : End Try
            If sCSSource <> "" AndAlso Not oActualMap.ContainsKey(sCSSource) Then
                oActualMap(sCSSource) = sPRFile
                iProvRebuild += 1
                Try : System.IO.File.AppendAllText(sLogPath, _
                    "PROV-REBUILD: " & System.IO.Path.GetFileName(sCSSource) & _
                    " -> " & System.IO.Path.GetFileName(sPRFile) & vbCrLf) : Catch : End Try
            End If
        Next
    Catch exPR As Exception
        Try : System.IO.File.AppendAllText(sLogPath, _
            "PROV-REBUILD-ERROR: " & exPR.Message & vbCrLf) : Catch : End Try
    End Try
    Try : System.IO.File.AppendAllText(sLogPath, _
        "Prov-rebuild complete: " & iProvRebuild & " prior mappings restored." & vbCrLf) : Catch : End Try

    Dim sOldFull2 As String
    For Each sOldFull2 In oMapKeys
        Dim sNewFull2 As String = oRenameMap(sOldFull2)
        Dim sOldName2 As String = System.IO.Path.GetFileName(sOldFull2)
        Dim sNewName2 As String = System.IO.Path.GetFileName(sNewFull2)
        Dim sExtU2    As String = System.IO.Path.GetExtension(sOldFull2).ToUpper()

        Try
            ' ── Provenance skip guard ────────────────────────────────────────
            ' v2.2.15: reused existing target — keep it as-is, no SaveAs
            If oReuseKeys.Contains(sOldFull2) AndAlso System.IO.File.Exists(sNewFull2) Then
                iSkipped += 1
                oActualMap(sOldFull2) = sNewFull2
                Try : System.IO.File.AppendAllText(sLogPath, _
                    "REUSE-SKIP: " & sOldName2 & "  ->  " & sNewName2 & vbCrLf) : Catch : End Try
                Continue For
            End If
            If IsAlreadyProcessed(sNewFull2, sNewPrefix) Then
                iSkipped += 1
                oActualMap(sOldFull2) = sNewFull2
                Try : System.IO.File.AppendAllText(sLogPath, _
                    "PROV-SKIP: " & sOldName2 & vbCrLf) : Catch : End Try
                Continue For
            End If

            ' ── Source file must exist ───────────────────────────────────────
            If Not System.IO.File.Exists(sOldFull2) Then
                iSaveFailed += 1
                Try : System.IO.File.AppendAllText(sLogPath, _
                    "SKIP-MISSING: " & sOldName2 & vbCrLf) : Catch : End Try
                Continue For
            End If

            ' ── Ensure destination directory exists ──────────────────────────
            Dim sDestDir2 As String = System.IO.Path.GetDirectoryName(sNewFull2)
            If Not System.IO.Directory.Exists(sDestDir2) Then
                Try : System.IO.Directory.CreateDirectory(sDestDir2) : Catch : End Try
            End If

            ' ── Open source document ─────────────────────────────────────────
            Dim oDoc2 As Document = Nothing
            Try : oDoc2 = ThisApplication.Documents.ItemByName(sOldFull2) : Catch : End Try
            Dim bOpenedHere2 As Boolean = False
            If oDoc2 Is Nothing Then
                Try
                    oDoc2 = ThisApplication.Documents.Open(sOldFull2, False)
                    bOpenedHere2 = True
                Catch exOpen2 As Exception
                    iSaveFailed += 1
                    Try : System.IO.File.AppendAllText(sLogPath, _
                        "OPEN-FAIL: " & sOldName2 & " — " & exOpen2.Message & vbCrLf) : Catch : End Try
                    Continue For
                End Try
            End If

            ' ── Capture GUID BEFORE SaveAs ───────────────────────────────────
            Dim sOldGUID2 As String = ""
            Try : sOldGUID2 = oDoc2.InternalName : Catch : End Try

            ' ── Read delta-provenance chain from SOURCE file ──────────────────
            ' If the source was already processed in a prior run, it carries
            ' CS_RootSource / CS_RootGUID / CS_RunCount.  Read and carry forward.
            ' If not, the source IS the root.
            Dim sRootSource2 As String = ""
            Dim sRootGUID2   As String = ""
            Dim iRunCount2   As Integer = 1
            Try
                sRootSource2 = oDoc2.PropertySets( _
                    "Inventor User Defined Properties").Item("CS_RootSource").Value
            Catch : End Try
            Try
                sRootGUID2 = oDoc2.PropertySets( _
                    "Inventor User Defined Properties").Item("CS_RootGUID").Value
            Catch : End Try
            Try
                Dim sRunStr As String = oDoc2.PropertySets( _
                    "Inventor User Defined Properties").Item("CS_RunCount").Value
                iRunCount2 = CInt(sRunStr) + 1
            Catch : End Try
            ' If source has no CS_RootSource, it IS the root
            If sRootSource2 = "" Then sRootSource2 = sOldFull2
            If sRootGUID2   = "" Then sRootGUID2   = sOldGUID2

            ' ── Collect old model refs from drawings ─────────────────────────
            Dim oModelRefs2 As New System.Collections.Generic.List(Of String)()
            If sExtU2 = ".IDW" OrElse sExtU2 = ".DWG" Then
                Try
                    For Each oDesc2 As Object In oDoc2.ReferencedDocumentDescriptors
                        Dim sRef2 As String = ""
                        Try : sRef2 = oDesc2.FullDocumentName : Catch : Continue For : End Try
                        Dim iAng2 As Integer = sRef2.IndexOf("<"c)
                        If iAng2 > 0 Then sRef2 = sRef2.Substring(0, iAng2)
                        sRef2 = sRef2.Trim()
                        If sRef2 <> "" Then oModelRefs2.Add(sRef2)
                    Next
                Catch : End Try
            End If

            ' ── SaveAs to new path (SaveCopyAs = True) ───────────────────────
            ' Primary path: oDoc.SaveAs with SaveCopyAs=True creates an independent
            ' copy with a fresh GUID (Inventor's preferred approach).
            ' Fallback path: System.IO.File.Copy — used when SaveAs returns
            ' E_INVALIDARG (0x80070057), which happens when the document is already
            ' open in the active Inventor session as a GA dependent (Vault-managed
            ' read-only session lock).  File.Copy bypasses the Inventor session
            ' entirely and writes a raw OS copy, which is then safe to open
            ' separately for provenance writing.
            ' v2.2.11: capture the source assembly's active design view before SaveAs
            Dim sSrcDV As String = ""
            If sExtU2 = ".IAM" AndAlso oDoc2 IsNot Nothing Then
                Try
                    Dim oSrcAsm As AssemblyDocument = TryCast(oDoc2, AssemblyDocument)
                    If oSrcAsm IsNot Nothing Then
                        sSrcDV = oSrcAsm.ComponentDefinition.RepresentationsManager.ActiveDesignViewRepresentation.Name
                    End If
                Catch : End Try
            End If

            Dim bSaveAsOk2 As Boolean = False
            Dim bUsedFileCopy2 As Boolean = False
            Try
                ThisApplication.SilentOperation = True
                oDoc2.SaveAs(sNewFull2, True)
                bSaveAsOk2 = System.IO.File.Exists(sNewFull2)
                ' FIX 8: Log if SaveAs returned no exception but output file not created
                If Not bSaveAsOk2 Then
                    Try : System.IO.File.AppendAllText(sLogPath, _
                        "SAVEAS-SILENT-FAIL: " & sOldName2 & _
                        " — SaveAs returned no exception but file not found on disk" & vbCrLf) : Catch : End Try
                End If
            Catch exSA2 As Exception
                Try : System.IO.File.AppendAllText(sLogPath, _
                    "SAVEAS-EXCEPTION: " & sOldName2 & _
                    " HRESULT=0x" & exSA2.HResult.ToString("X8") & _
                    " — " & exSA2.Message & vbCrLf) : Catch : End Try

                ' Inventor can create the destination and still throw during SaveAs.
                ' Never overwrite or silently claim an unrelated existing file.
                If System.IO.File.Exists(sNewFull2) Then
                    Try : System.IO.File.AppendAllText(sLogPath, _
                        "SAVEAS-PARTIAL: " & sNewName2 & _
                        " exists after exception; verify before accepting" & vbCrLf) : Catch : End Try
                    bSaveAsOk2 = False
                Else
                    Try
                        System.IO.File.Copy(sOldFull2, sNewFull2, False)
                        bSaveAsOk2 = System.IO.File.Exists(sNewFull2)
                        bUsedFileCopy2 = bSaveAsOk2
                        If bSaveAsOk2 Then
                            Try : System.IO.File.AppendAllText(sLogPath, _
                                "SAVEAS-FALLBACK-COPY: " & sOldName2 & _
                                " -> " & sNewName2 & _
                                " [raw copy; references require validation]" & vbCrLf) : Catch : End Try
                        End If
                    Catch exFC2 As Exception
                        Try : System.IO.File.AppendAllText(sLogPath, _
                            "FILECOPY-FAIL: " & sOldName2 & _
                            " HRESULT=0x" & exFC2.HResult.ToString("X8") & _
                            " — " & exFC2.Message & vbCrLf) : Catch : End Try
                    End Try
                End If
                If Not bSaveAsOk2 Then
                    Try : System.IO.File.AppendAllText(sLogPath, _
                        "SAVEAS-FAIL: " & sOldName2 & " — " & exSA2.Message & vbCrLf) : Catch : End Try
                End If
            End Try

            ' A successful COM return is not proof that SaveAs created a file.
            ' Use the same non-overwriting fallback for silent failures.
            If Not bSaveAsOk2 AndAlso Not System.IO.File.Exists(sNewFull2) Then
                Try
                    System.IO.File.Copy(sOldFull2, sNewFull2, False)
                    bSaveAsOk2 = System.IO.File.Exists(sNewFull2)
                    bUsedFileCopy2 = bSaveAsOk2
                    If bSaveAsOk2 Then
                        Try : System.IO.File.AppendAllText(sLogPath, _
                            "SAVEAS-SILENT-FALLBACK-COPY: " & sOldName2 & " -> " & sNewName2 & _
                            " [raw copy; references require validation]" & vbCrLf) : Catch : End Try
                    End If
                Catch exSilentFC2 As Exception
                    Try : System.IO.File.AppendAllText(sLogPath, _
                        "SAVEAS-SILENT-FALLBACK-FAIL: " & sOldName2 & _
                        " HRESULT=0x" & exSilentFC2.HResult.ToString("X8") & _
                        " — " & exSilentFC2.Message & vbCrLf) : Catch : End Try
                End Try
            End If

            If bSaveAsOk2 Then
                ' Clear RO on new file
                Try
                    Dim oNA2 As System.IO.FileAttributes = System.IO.File.GetAttributes(sNewFull2)
                    If (oNA2 And System.IO.FileAttributes.ReadOnly) = System.IO.FileAttributes.ReadOnly Then
                        System.IO.File.SetAttributes(sNewFull2, oNA2 And Not System.IO.FileAttributes.ReadOnly)
                    End If
                Catch : End Try

                ' ── Open new file and write provenance ───────────────────────
                ' IMPORTANT: Skip opening .iam copies that came via File.Copy.
                ' Opening a File.Copied .iam whose internal refs still point to
                ' the original source paths can trigger resolve/Vault dialogs
                ' that hang Inventor even with SilentOperation=True (DA assemblies
                ' bypass SilentOperation for unresolved references).
                ' Provenance on these .iam files is deferred to Phase 3 (after
                ' refs are relinked and the assembly loads cleanly).
                ' .ipt File.Copy results are safe to open — they have no sub-refs.
                If bUsedFileCopy2 AndAlso sExtU2 = ".IAM" Then
                    oActualMap(sOldFull2) = sNewFull2
                    oCreatedThisRun.Add(sNewFull2)
                    iSaved += 1
                    Try : System.IO.File.AppendAllText(sLogPath, _
                        "COPY+DEFER-PROV: " & sOldName2 & "  ->  " & sNewName2 & _
                        "  [provenance deferred — .iam open skipped to avoid hang]" & vbCrLf) : Catch : End Try
                    If bOpenedHere2 AndAlso oDoc2 IsNot Nothing Then
                        Try : oDoc2.Close(True) : Catch : End Try
                    End If
                    Continue For
                End If

                Dim oNewDoc2 As Document = Nothing
                Try
                    ThisApplication.SilentOperation = True
                    oNewDoc2 = ThisApplication.Documents.Open(sNewFull2, False)
                Catch exOpenNew2 As Exception
                    Try : System.IO.File.AppendAllText(sLogPath, _
                        "NEW-OPEN-FAIL: " & sNewName2 & " — " & exOpenNew2.Message & vbCrLf) : Catch : End Try
                End Try

                If oNewDoc2 IsNot Nothing Then
                    ' Write 8-property delta-provenance chain
                    WriteProvenanceProps(oNewDoc2, sOldFull2, sNewPrefix, sOldGUID2, _
                                         sRootSource2, sRootGUID2, iRunCount2, sLogPath)

                    ' Write CS_ModelRefs for drawing files
                    If (sExtU2 = ".IDW" OrElse sExtU2 = ".DWG") AndAlso _
                       oModelRefs2.Count > 0 Then
                        WriteDrawingModelRefs(oNewDoc2, oModelRefs2, sLogPath)
                    End If

                    ' v2.2.11: activate the source's design view in the new assembly
                    If sSrcDV <> "" AndAlso sExtU2 = ".IAM" Then
                        Try
                            Dim oNewAsm As AssemblyDocument = TryCast(oNewDoc2, AssemblyDocument)
                            If oNewAsm IsNot Nothing Then
                                oNewAsm.ComponentDefinition.RepresentationsManager.DesignViewRepresentations.Item(sSrcDV).Activate()
                                Try : System.IO.File.AppendAllText(sLogPath, "DV-ACTIVATE: " & sNewName2 & " -> " & sSrcDV & vbCrLf) : Catch : End Try
                                ' v2.2.13: on the top GA, set this design view as the default so the file opens in it
                                If String.Equals(sOldFull2, sTopFull, StringComparison.OrdinalIgnoreCase) Then
                                    Try
                                        Dim oDV As DesignViewRepresentation = oNewAsm.ComponentDefinition.RepresentationsManager.DesignViewRepresentations.Item(sSrcDV)
                                        oDV.Activate()
                                        ' Inventor has no direct SetAsDefault; the active view at save time becomes the open view.
                                        ' Save2(False) follows below. Log it.
                                        Try : System.IO.File.AppendAllText(sLogPath, "DV-DEFAULT: " & sNewName2 & " -> " & sSrcDV & vbCrLf) : Catch : End Try
                                    Catch
                                        Try : System.IO.File.AppendAllText(sLogPath, "DV-DEFAULT-FAIL: " & sNewName2 & vbCrLf) : Catch : End Try
                                    End Try
                                End If
                            End If
                        Catch exDV As Exception
                            Try : System.IO.File.AppendAllText(sLogPath, "DV-FAIL: " & sNewName2 & " (" & sSrcDV & ") — " & exDV.Message & vbCrLf) : Catch : End Try
                        End Try
                    End If

                    ' Save provenance to disk  ' FIX C: Save2(False) — no cascade to dirty dependents
                    Try
                        oNewDoc2.Save2(False)
                    Catch exSvProv2 As Exception
                        Try : System.IO.File.AppendAllText(sLogPath, _
                            "PROV-SAVE-FAIL: " & sNewName2 & " — " & exSvProv2.Message & vbCrLf) : Catch : End Try
                    End Try

                    Try : oNewDoc2.Close(True) : Catch : End Try

                    Dim sSaveMethod2 As String = If(bUsedFileCopy2, "COPY+PROV", "SAVED+PROV")
                    Try : System.IO.File.AppendAllText(sLogPath, _
                        sSaveMethod2 & ": " & sOldName2 & "  ->  " & sNewName2 & _
                        "  [OldGUID:" & sOldGUID2 & "  Run:" & iRunCount2 & "]" & vbCrLf) : Catch : End Try
                Else
                    ' FIX 9: File saved but provenance not written — log distinctly
                    iNoProvenance += 1
                    Try : System.IO.File.AppendAllText(sLogPath, _
                        "SAVED-NO-PROV: " & sNewName2 & _
                        " — saved but provenance not written (new-file open failed)" & vbCrLf) : Catch : End Try
                End If

                oActualMap(sOldFull2) = sNewFull2
                oCreatedThisRun.Add(sNewFull2)
                iSaved += 1
            Else
                iSaveFailed += 1
            End If

            ' ── Close source if we opened it ─────────────────────────────────
            If bOpenedHere2 AndAlso oDoc2 IsNot Nothing Then
                Try : oDoc2.Close(True) : Catch : End Try
            End If

        Catch exOuter2 As Exception
            iSaveFailed += 1
            Try : System.IO.File.AppendAllText(sLogPath, _
                "P2-ERROR: " & sOldName2 & " — " & exOuter2.Message & vbCrLf) : Catch : End Try
        End Try
    Next

    Try : System.IO.File.AppendAllText(sLogPath, _
        "Phase 2 complete: " & iSaved & " saved, " & _
        iSkipped & " prov-skipped, " & iSaveFailed & " failed, " & _
        iNoProvenance & " saved-no-prov." & vbCrLf) : Catch : End Try

    ' ── 7. PHASE 3 — Fix internal references ─────────────────────────────────
    ' APPROACH (from old Traverse rule code-assassin analysis):
    '   3a) File.ReferencedFileDescriptors + FD.ReplaceReference
    '       — E_INVALIDARG (0x80070057) on this call means the FD is locked
    '         (CC/DA part).  This is a SAFE SKIP, not a failure.
    '         The old Traverse rule explicitly treats HResult &H80070057 as skip.
    '   3b) ComponentOccurrence.Replace(newPath, False)
    '       — The REAL workhorse for Design Accelerator and library parts.
    '         Works even when FD.ReplaceReference throws E_INVALIDARG.
    '
    ' Document source: open files in isolation (deepest-first from oActualMap)
    ' because AllReferencedDocuments also returns E_INVALIDARG for the same FDs.
    ' Opening in isolation IS correct here — 3b uses Occurrence.Replace which
    ' doesn't depend on the parent context.
    Try : System.IO.File.AppendAllText(sLogPath, vbCrLf & "=== PHASE 3: FIX INTERNAL REFS ===" & vbCrLf) : Catch : End Try

    ' Build a basename->full-path lookup for every file on disk in target folder
    Dim oTargetByBase As New System.Collections.Generic.Dictionary(Of String, String)( _
        StringComparer.OrdinalIgnoreCase)
    Try  ' FIX F: *.iam + *.ipt only — avoids indexing PDFs/DWGs/logs on large targets
        For Each sTF As String In System.IO.Directory.GetFiles(sTargetFolder, "*.iam", _
                System.IO.SearchOption.TopDirectoryOnly)
            Dim sTFBase As String = System.IO.Path.GetFileName(sTF)
            If Not oTargetByBase.ContainsKey(sTFBase) Then oTargetByBase(sTFBase) = sTF
        Next
        For Each sTF As String In System.IO.Directory.GetFiles(sTargetFolder, "*.ipt", _
                System.IO.SearchOption.TopDirectoryOnly)
            Dim sTFBase As String = System.IO.Path.GetFileName(sTF)
            If Not oTargetByBase.ContainsKey(sTFBase) Then oTargetByBase(sTFBase) = sTF
        Next
    Catch : End Try

    ' Build full list of new .iam/.ipt files to process — from oActualMap values
    ' PLUS any .iam already in target folder not in this run (PROV-SKIPs).
    Dim oP3Targets As New System.Collections.Generic.List(Of String)()
    Dim oP3Seen As New System.Collections.Generic.HashSet(Of String)(StringComparer.OrdinalIgnoreCase)
    ' Add all from oActualMap (files SaveAs'd or skipped this run)
    For Each sV3 As String In oActualMap.Values
        Dim sVExtU3 As String = System.IO.Path.GetExtension(sV3).ToUpper()
        If (sVExtU3 = ".IAM" OrElse sVExtU3 = ".IPT") AndAlso Not oP3Seen.Contains(sV3) Then
            oP3Seen.Add(sV3)
            oP3Targets.Add(sV3)
        End If
    Next
    ' FIX 6: Use oTargetByBase (already built above) instead of a redundant
    '        second GetFiles("*.iam") disk call.
    For Each sKV3 As String In oTargetByBase.Values
        If System.IO.Path.GetExtension(sKV3).ToUpper() = ".IAM" AndAlso Not oP3Seen.Contains(sKV3) Then
            oP3Seen.Add(sKV3)
            oP3Targets.Add(sKV3)
        End If
    Next
    ' Process deepest-first (longest path = deepest)
    oP3Targets.Sort(Function(a2, b2) b2.Length.CompareTo(a2.Length))

    Dim sNewPath3 As String
    ' v2.2.4: refs are counted as fixed only after the document saves.
    Dim iPending3 As Integer = 0
    Dim bSaved3 As Boolean = False
    For Each sNewPath3 In oP3Targets
        iPending3 = 0
        bSaved3 = False
        Dim sNewName3 As String = System.IO.Path.GetFileName(sNewPath3)
        Dim sExtU3    As String = System.IO.Path.GetExtension(sNewPath3).ToUpper()
        If Not System.IO.File.Exists(sNewPath3) Then Continue For
        ' v2.2.17: never open or save a file this run did not create
        If Not oCreatedThisRun.Contains(sNewPath3) Then
            Try : System.IO.File.AppendAllText(sLogPath, "P3-SKIP-NOT-CREATED: " & sNewName3 & vbCrLf) : Catch : End Try
            Continue For
        End If

        ' Open the new file (SilentOperation to suppress Vault dialogs)
        Dim bOpened3  As Boolean  = False
        Dim oDoc3     As Document = Nothing
        Try : oDoc3 = ThisApplication.Documents.ItemByName(sNewPath3) : Catch : End Try
        If oDoc3 Is Nothing Then
            Try
                ThisApplication.SilentOperation = True
                oDoc3 = ThisApplication.Documents.Open(sNewPath3, False)
                bOpened3 = True
            Catch exOpen3 As Exception
                Try : System.IO.File.AppendAllText(sLogPath, _
                    "P3-OPEN-FAIL: " & sNewName3 & " — " & exOpen3.Message & vbCrLf) : Catch : End Try
                Continue For
            End Try
        End If
        If oDoc3 Is Nothing Then Continue For

        ' Helper: resolve old ref path → new path
        ' Uses oActualMap first, then basename fallback in target folder
        Dim bChanged3 As Boolean = False

        Try
            ' ── 3a: File.ReferencedFileDescriptors ─────────────────────────
            ' E_INVALIDARG (HResult &H80070057) = CC/DA locked FD — safe skip
            If oDoc3.File IsNot Nothing Then
                Try
                    For Each oFD3 As Object In oDoc3.File.ReferencedFileDescriptors
                        Dim sOldRef3 As String = ""
                        Try : sOldRef3 = oFD3.FullFileName : Catch : Continue For : End Try
                        If sOldRef3 = "" Then Continue For
                        If IsSameOrUnderDirectory(sOldRef3, sTargetFolder) Then Continue For

                        Dim sNewRef3 As String = ""
                        If oActualMap.ContainsKey(sOldRef3) Then
                            sNewRef3 = oActualMap(sOldRef3)
                        Else
                            Dim sB3 As String = System.IO.Path.GetFileName(sOldRef3)
                            If oTargetByBase.ContainsKey(sB3) Then sNewRef3 = oTargetByBase(sB3)
                        End If
                        If sNewRef3 = "" OrElse Not System.IO.File.Exists(sNewRef3) Then Continue For
                        If String.Compare(sOldRef3, sNewRef3, True) = 0 Then Continue For

                        Try
                            oFD3.ReplaceReference(sNewRef3)
                            bChanged3 = True
                            iPending3 += 1
                            Try : System.IO.File.AppendAllText(sLogPath, _
                                "  P3-FD: [" & sNewName3 & "] " & _
                                System.IO.Path.GetFileName(sOldRef3) & " -> " & _
                                System.IO.Path.GetFileName(sNewRef3) & vbCrLf) : Catch : End Try
                        Catch exFD3 As Exception
                            ' E_INVALIDARG = CC/DA locked — safe skip (old Traverse behaviour)
                            If exFD3.HResult = &H80070057 Then
                                Try : System.IO.File.AppendAllText(sLogPath, _
                                    "  P3-FD-SKIP(locked): [" & sNewName3 & "] " & _
                                    System.IO.Path.GetFileName(sOldRef3) & vbCrLf) : Catch : End Try
                            Else
                                iRefFailed += 1
                                Try : System.IO.File.AppendAllText(sLogPath, _
                                    "  P3-FD-FAIL: [" & sNewName3 & "] " & _
                                    System.IO.Path.GetFileName(sOldRef3) & " — " & exFD3.Message & vbCrLf) : Catch : End Try
                            End If
                        End Try
                    Next
                Catch exFDW3 As Exception
                    Try : System.IO.File.AppendAllText(sLogPath, _
                        "P3-FD-WALK-FAIL: " & sNewName3 & " — " & exFDW3.Message & vbCrLf) : Catch : End Try
                End Try
            End If

            ' ── 3b: ComponentOccurrence.Replace — the real workhorse ───────
            ' Handles DA-managed parts, library parts, anything FD can't fix.
            If sExtU3 = ".IAM" Then
                Try
                    ' FIX 7: Guard TryCast result before accessing .ComponentDefinition
                    '        to prevent NullReferenceException on corrupt .IAM files.
                    Dim oAsmDoc3 As AssemblyDocument = TryCast(oDoc3, AssemblyDocument)
                    If oAsmDoc3 Is Nothing Then Continue For
                    Dim oAsmDef3 As AssemblyComponentDefinition = oAsmDoc3.ComponentDefinition
                    If oAsmDef3 IsNot Nothing Then
                        ' Snapshot occurrences first to avoid collection-modified errors
                        Dim oOccSnap3 As New System.Collections.Generic.List(Of ComponentOccurrence)()
                        Try
                            For Each oOcc3Snap As ComponentOccurrence In oAsmDef3.Occurrences
                                oOccSnap3.Add(oOcc3Snap)
                            Next
                        Catch : End Try

                        For Each oOcc3 As ComponentOccurrence In oOccSnap3
                            Dim sOccOld3 As String = ""
                            Try : sOccOld3 = oOcc3.Definition.Document.FullFileName : Catch
                                Try : sOccOld3 = oOcc3.ReferencedFileDescriptor.FullFileName : Catch : Continue For : End Try
                            End Try
                            If sOccOld3 = "" Then Continue For
                            If IsSameOrUnderDirectory(sOccOld3, sTargetFolder) Then Continue For

                            Dim sOccNew3 As String = ""
                            If oActualMap.ContainsKey(sOccOld3) Then
                                sOccNew3 = oActualMap(sOccOld3)
                            Else
                                Dim sBOcc3 As String = System.IO.Path.GetFileName(sOccOld3)
                                If oTargetByBase.ContainsKey(sBOcc3) Then sOccNew3 = oTargetByBase(sBOcc3)
                            End If
                            If sOccNew3 = "" OrElse Not System.IO.File.Exists(sOccNew3) Then Continue For
                            If String.Compare(sOccOld3, sOccNew3, True) = 0 Then Continue For

                            Dim bReplaced3 As Boolean = False
                            Try
                                oOcc3.Replace(sOccNew3, False)
                                bReplaced3 = True
                            Catch
                                ' Fallback: try FD on the occurrence's own descriptor
                                Try
                                    Dim oFD3b As FileDescriptor = oOcc3.ReferencedFileDescriptor
                                    If oFD3b IsNot Nothing Then
                                        oFD3b.ReplaceReference(sOccNew3)
                                        bReplaced3 = True
                                    End If
                                Catch : End Try
                            End Try

                            If bReplaced3 Then
                                bChanged3 = True
                                iPending3 += 1
                                Try : oOcc3.Name = System.IO.Path.GetFileNameWithoutExtension(sOccNew3) : Catch : End Try
                                Try : System.IO.File.AppendAllText(sLogPath, _
                                    "  P3-OCC: [" & sNewName3 & "] " & _
                                    System.IO.Path.GetFileName(sOccOld3) & " -> " & _
                                    System.IO.Path.GetFileName(sOccNew3) & vbCrLf) : Catch : End Try
                            End If
                        Next
                    End If
                Catch exOcc3 As Exception
                    Try : System.IO.File.AppendAllText(sLogPath, _
                        "P3-OCC-FAIL: " & sNewName3 & " — " & exOcc3.Message & vbCrLf) : Catch : End Try
                End Try
            End If

        Catch exP3 As Exception
            iRefFailed += 1
            Try : System.IO.File.AppendAllText(sLogPath, _
                "P3-ERROR: " & sNewName3 & " — " & exP3.Message & vbCrLf) : Catch : End Try
        End Try

        ' v2.2.31: deferred provenance for raw-copied assemblies.
        ' Write only to a new document from this run, never to its source.
        Dim bProvChanged3 As Boolean = False
        If sExtU3 = ".IAM" Then
            Try
                Dim sProvOld3 As String = ""
                For Each oProvPair3 As System.Collections.Generic.KeyValuePair(Of String, String) In oActualMap
                    If String.Equals(oProvPair3.Value, sNewPath3, StringComparison.OrdinalIgnoreCase) Then
                        sProvOld3 = oProvPair3.Key
                        Exit For
                    End If
                Next
                If sProvOld3 <> "" Then
                    Dim sExistingProv3 As String = ""
                    Try : sExistingProv3 = CStr(oDoc3.PropertySets.Item("Inventor User Defined Properties").Item("CS_SourcePath").Value) : Catch : End Try
                    If sExistingProv3 = "" Then
                        SetSweeperCopyProperty(oDoc3, "CS_SourcePath", sProvOld3)
                        SetSweeperCopyProperty(oDoc3, "CS_CopyProject", sNewPrefix)
                        SetSweeperCopyProperty(oDoc3, "CS_CopyDate", Now.ToString("yyyy-MM-dd"))
                        bProvChanged3 = True
                        Try : System.IO.File.AppendAllText(sLogPath, _
                            "P3-DEFERRED-PROV: " & sNewName3 & vbCrLf) : Catch : End Try
                    End If
                End If
            Catch exProv3 As Exception
                Try : System.IO.File.AppendAllText(sLogPath, _
                    "P3-DEFERRED-PROV-FAIL: " & sNewName3 & " — " & exProv3.Message & vbCrLf) : Catch : End Try
            End Try
        End If

        ' Save if changed, then close if we opened it
        If bChanged3 OrElse bProvChanged3 Then
            ' Clear RO before save
            Try
                Dim oFA3 As System.IO.FileAttributes = System.IO.File.GetAttributes(sNewPath3)
                If (oFA3 And System.IO.FileAttributes.ReadOnly) = System.IO.FileAttributes.ReadOnly Then
                    System.IO.File.SetAttributes(sNewPath3, oFA3 And Not System.IO.FileAttributes.ReadOnly)
                End If
            Catch : End Try
            ' SilentOperation = True suppresses Inventor's multi-file Save dialog
            ' ("Multiple files have been updated in current session...") that fires
            ' when saving an assembly whose referenced CC/library parts are dirty.
            ' Save2(False): save this document only, do not cascade to dirty
            ' CC/library dependents that Vault would prompt about.
            ' v2.2.4: no fallback to Save(); log the exact Save2 error instead.
            Try
                ThisApplication.SilentOperation = True
                oDoc3.Save2(False)
                bSaved3 = True
                iRefFixed += iPending3
                Try
                    System.IO.File.AppendAllText(sLogPath, "P3-SAVED: " & sNewName3 & _
                        " (" & iPending3 & " ref(s))" & vbCrLf)
                Catch
                End Try
            Catch exSv3 As Exception
                iRefFailed += iPending3
                Try
                    System.IO.File.AppendAllText(sLogPath, _
                        "P3-SAVE2-FAIL: " & sNewName3 & " — " & exSv3.Message & _
                        "  (left open for retry; " & iPending3 & " ref(s) not counted as fixed)" & vbCrLf)
                Catch
                End Try
            End Try
        Else
            bSaved3 = True
        End If
        ' Close only if the save succeeded (or nothing needed saving) AND we opened it here.
        If bSaved3 AndAlso bOpened3 AndAlso oDoc3 IsNot Nothing Then
            Try
                oDoc3.Close(True)
            Catch
            End Try
        End If
    Next

    Try : System.IO.File.AppendAllText(sLogPath, _
        "Phase 3 complete: " & iRefFixed & " fixed, " & iRefFailed & " failed." & vbCrLf) : Catch : End Try

    ' ── PHASE 4: LIVE OCCURRENCE RESWEEP on the active GA ──────────────────────
    ' Runs after Phase 3. Opens the new top GA visibly and walks ComponentOccurrences
    ' bottom-up. For any occurrence still pointing at an old path that has a target
    ' in oActualMap, calls ComponentOccurrence.Replace. Clears read-only before save.
    ' Never closes a document with unsaved changes via Close(True).
    ' Browser rename is deferred.
    Try
        System.IO.File.AppendAllText(sLogPath, vbCrLf & "=== PHASE 4: LIVE OCCURRENCE RESWEEP ===" & vbCrLf)
        Dim sNewGAPath As String = ""
        If oActualMap.ContainsKey(sTopFull) Then sNewGAPath = oActualMap(sTopFull)
        ' v2.2.5: on a rerun the active GA may already be the new GA in the target folder.
        If sNewGAPath = "" AndAlso IsSameOrUnderDirectory(sTopFull, sTargetFolder) Then sNewGAPath = sTopFull
        If sNewGAPath <> "" AndAlso System.IO.File.Exists(sNewGAPath) Then
            Dim oNewGA As AssemblyDocument = Nothing
            Dim bGAOpenedHere As Boolean = False
            Try
                oNewGA = TryCast(ThisApplication.Documents.ItemByName(sNewGAPath), AssemblyDocument)
            Catch : End Try
            If oNewGA Is Nothing Then
                Try
                    oNewGA = TryCast(ThisApplication.Documents.Open(sNewGAPath, True), AssemblyDocument)
                    bGAOpenedHere = True
                Catch exGA As Exception
                    Try : System.IO.File.AppendAllText(sLogPath, "P4-OPEN-FAIL: " & exGA.Message & vbCrLf) : Catch : End Try
                End Try
            End If
            If oNewGA IsNot Nothing Then
                Dim iP4Fixed As Integer = 0
                Dim iP4Failed As Integer = 0
                Dim oP4Visited As New System.Collections.Generic.HashSet(Of String)()
                Phase4_WalkOccs(oNewGA.ComponentDefinition, oActualMap, oTargetByBase, sTargetFolder, sLogPath, oP4Visited, iP4Fixed, iP4Failed)
                ' Save the GA after the walk
                Try
                    Dim oFA4 As System.IO.FileAttributes = System.IO.File.GetAttributes(sNewGAPath)
                    If (oFA4 And System.IO.FileAttributes.ReadOnly) = System.IO.FileAttributes.ReadOnly Then
                        System.IO.File.SetAttributes(sNewGAPath, oFA4 And Not System.IO.FileAttributes.ReadOnly)
                    End If
                    oNewGA.Save2(False)
                    Try : System.IO.File.AppendAllText(sLogPath, "P4-GA-SAVED: " & System.IO.Path.GetFileName(sNewGAPath) & vbCrLf) : Catch : End Try
                Catch exGASave As Exception
                    Try : System.IO.File.AppendAllText(sLogPath, "P4-GA-SAVE-FAIL: " & exGASave.Message & vbCrLf) : Catch : End Try
                End Try
                Try : System.IO.File.AppendAllText(sLogPath, "Phase 4 complete: " & iP4Fixed & " replaced, " & iP4Failed & " failed." & vbCrLf) : Catch : End Try
                ' v2.2.12: leave the new GA open so it can be checked straight away.
                sKeepOpenGA = sNewGAPath
                Try
                    If oNewGA.Views.Count = 0 Then
                        oNewGA.Views.Add()
                        Try : System.IO.File.AppendAllText(sLogPath, "P4-GA-SHOWN: " & System.IO.Path.GetFileName(sNewGAPath) & vbCrLf) : Catch : End Try
                    End If
                Catch : End Try
                Try : System.IO.File.AppendAllText(sLogPath, "P4-GA-LEFT-OPEN: " & System.IO.Path.GetFileName(sNewGAPath) & vbCrLf) : Catch : End Try
            End If
        Else
            Try : System.IO.File.AppendAllText(sLogPath, "P4-SKIP: new GA path not found in map." & vbCrLf) : Catch : End Try
        End If
    Catch exP4 As Exception
        Try : System.IO.File.AppendAllText(sLogPath, "P4-ERROR: " & exP4.Message & vbCrLf) : Catch : End Try
    End Try

    ' ── BROWSER RENAME (v2.2.14): occurrence names = new filenames ─────────────
    ' Walks the new top GA (reusing the Phase 4 document if still open) and sets
    ' each target-folder occurrence's browser Name to its filename without
    ' extension.  SilentOperation stays True.  The GA is left open.
    Try
        Try : System.IO.File.AppendAllText(sLogPath, vbCrLf & "=== BROWSER RENAME ===" & vbCrLf) : Catch : End Try
        ThisApplication.SilentOperation = True
        Dim sBRPath As String = sKeepOpenGA
        If sBRPath = "" Then
            If oActualMap.ContainsKey(sTopFull) Then sBRPath = oActualMap(sTopFull)
            If sBRPath = "" AndAlso IsSameOrUnderDirectory(sTopFull, sTargetFolder) Then sBRPath = sTopFull
        End If
        If sBRPath <> "" AndAlso System.IO.File.Exists(sBRPath) Then
            Dim oBRGA As AssemblyDocument = Nothing
            Try
                oBRGA = TryCast(ThisApplication.Documents.ItemByName(sBRPath), AssemblyDocument)
            Catch
            End Try
            If oBRGA Is Nothing Then
                Try
                    oBRGA = TryCast(ThisApplication.Documents.Open(sBRPath, True), AssemblyDocument)
                Catch exBROpen As Exception
                    Try : System.IO.File.AppendAllText(sLogPath, "BROWSER-RENAME-OPEN-FAIL: " & exBROpen.Message & vbCrLf) : Catch : End Try
                End Try
            End If
            If oBRGA IsNot Nothing Then
                sKeepOpenGA = sBRPath
                Dim iBRRenamed As Integer = 0
                Dim oBRVisited As New System.Collections.Generic.HashSet(Of String)(StringComparer.OrdinalIgnoreCase)
                BrowserRename_WalkOccs(oBRGA.ComponentDefinition, sBRPath, sTargetFolder, sLogPath, oBRVisited, iBRRenamed)
                If iBRRenamed > 0 Then
                    Try
                        Dim oFABR As System.IO.FileAttributes = System.IO.File.GetAttributes(sBRPath)
                        If (oFABR And System.IO.FileAttributes.ReadOnly) = System.IO.FileAttributes.ReadOnly Then
                            System.IO.File.SetAttributes(sBRPath, oFABR And Not System.IO.FileAttributes.ReadOnly)
                        End If
                        oBRGA.Save2(False)
                        Try : System.IO.File.AppendAllText(sLogPath, "BROWSER-RENAME-SAVED: " & System.IO.Path.GetFileName(sBRPath) & vbCrLf) : Catch : End Try
                    Catch exBRSave As Exception
                        Try : System.IO.File.AppendAllText(sLogPath, "BROWSER-RENAME-SAVE-FAIL: " & exBRSave.Message & vbCrLf) : Catch : End Try
                    End Try
                End If
                Try : System.IO.File.AppendAllText(sLogPath, "Browser rename complete: " & iBRRenamed & " renamed." & vbCrLf) : Catch : End Try
            End If
        Else
            Try : System.IO.File.AppendAllText(sLogPath, "BROWSER-RENAME-SKIP: new GA path not found." & vbCrLf) : Catch : End Try
        End If
    Catch exBR As Exception
        Try : System.IO.File.AppendAllText(sLogPath, "BROWSER-RENAME-ERROR: " & exBR.Message & vbCrLf) : Catch : End Try
    End Try

    ' ── FINAL DEFAULT DESIGN VIEW (v2.2.18 CA-fixes): show "Default" on the open top GA ──
    Try
        ' FIX 1: Prefer sKeepOpenGA (the definitive new GA set by Phase 4 / browser-rename)
        ' over ActiveDocument.  ActiveDocument can be the original GA or any other assembly
        ' if Inventor shifted focus during the browser-rename or drawing-relink pass.
        Dim oFinalGA As AssemblyDocument = Nothing
        If sKeepOpenGA <> "" Then
            Try : oFinalGA = TryCast(ThisApplication.Documents.ItemByName(sKeepOpenGA), AssemblyDocument) : Catch : End Try  ' FIX 2: inner Try/Catch — COM error falls through to ActiveDocument fallback
        End If
        If oFinalGA Is Nothing Then
            oFinalGA = TryCast(ThisApplication.ActiveDocument, AssemblyDocument)
        End If
        If oFinalGA IsNot Nothing Then
            ' FIX 3: Locale-safe lookup — Inventor localises "Default" in some regions (e.g. "Standard" in German).
            Dim oDVMgr As RepresentationsManager = oFinalGA.ComponentDefinition.RepresentationsManager
            Dim oDefDV As DesignViewRepresentation = Nothing
            Dim oDVItem As DesignViewRepresentation
            For Each oDVItem In oDVMgr.DesignViewRepresentations
                If String.Equals(oDVItem.Name, "Default", StringComparison.OrdinalIgnoreCase) OrElse _
                   String.Equals(oDVItem.Name, "Standard", StringComparison.OrdinalIgnoreCase) Then
                    oDefDV = oDVItem : Exit For
                End If
            Next
            If oDefDV IsNot Nothing Then
                oDefDV.Activate()
                Try : System.IO.File.AppendAllText(sLogPath, "FINAL-DV: Default activated on " & System.IO.Path.GetFileName(oFinalGA.FullFileName) & vbCrLf) : Catch : End Try
            Else
                Try : System.IO.File.AppendAllText(sLogPath, "FINAL-DV-SKIP: no Default design view found on " & System.IO.Path.GetFileName(oFinalGA.FullFileName) & vbCrLf) : Catch : End Try
            End If
        End If
    Catch exFinalDV As Exception
        Try : System.IO.File.AppendAllText(sLogPath, "FINAL-DV-FAIL: " & exFinalDV.Message & vbCrLf) : Catch : End Try
    End Try

    ' F1: Finally block — SilentOperation restored even if Phase 2/3 throws
    Finally
        ThisApplication.SilentOperation = bOrigSilent
        ' FIX 1: Close all documents opened in PRE-PHASE 2 for provenance rebuild.
        ' These were not tracked by Phase 2's bOpenedHere2 flag and were left open
        ' intentionally until this point to allow Phase 3 to use them if needed.
        ' v2.2.12: skip the close for the new GA that Phase 4 left open.
        Dim sPRDFull As String
        For Each oPRD As Document In oProvRebuildOpened
            sPRDFull = ""
            Try
                sPRDFull = oPRD.FullFileName
            Catch
            End Try
            If sKeepOpenGA <> "" AndAlso String.Equals(sPRDFull, sKeepOpenGA, StringComparison.OrdinalIgnoreCase) Then Continue For
            Try : oPRD.Close(True) : Catch : End Try
        Next
    End Try  ' ← F1: outer Try/Finally ends here

    End If  ' Not bRelinkOnly

    If bRelinkOnly Then
        Try : System.IO.File.AppendAllText(sLogPath, vbCrLf & "=== RELINK-ONLY MAP ===" & vbCrLf) : Catch : End Try
        Dim sROFile As String
        Dim sROSource As String
        Dim oROCache As New System.Collections.Generic.Dictionary(Of String, String)(StringComparer.OrdinalIgnoreCase)
        For Each sROFile In System.IO.Directory.GetFiles(sTargetFolder, "*.iam", System.IO.SearchOption.TopDirectoryOnly)
            sROSource = ReadCSSourcePath(sROFile, oROCache)
            If sROSource <> "" AndAlso Not oActualMap.ContainsKey(sROSource) Then
                oActualMap(sROSource) = sROFile
            End If
        Next
        For Each sROFile In System.IO.Directory.GetFiles(sTargetFolder, "*.ipt", System.IO.SearchOption.TopDirectoryOnly)
            sROSource = ReadCSSourcePath(sROFile, oROCache)
            If sROSource <> "" AndAlso Not oActualMap.ContainsKey(sROSource) Then
                oActualMap(sROSource) = sROFile
            End If
        Next
        Try : System.IO.File.AppendAllText(sLogPath, "RELINK-ONLY: map entries from CS_SourcePath = " & oActualMap.Count.ToString() & vbCrLf) : Catch : End Try
    End If


    ' ── Type B orphan copy (v2.2.27) ─────────────────────────────────────────
    ' Models referenced by a drawing but not in the GA map are copied
    ' independently with the new prefix and added to oActualMap.
    Try : System.IO.File.AppendAllText(sLogPath, vbCrLf & "=== TYPE B ORPHANS ===" & vbCrLf) : Catch : End Try
    Dim oOrphanSeen As New System.Collections.Generic.HashSet(Of String)(StringComparer.OrdinalIgnoreCase)
    Dim sOrphDwg As String
    Dim sOrphModel As String
    Dim sOrphNew As String
    Dim oOrphDoc As Document
    Dim iOrphCount As Integer = 0
    For Each sOrphDwg In oDwgModels.Keys
        For Each sOrphModel In oDwgModels(sOrphDwg)
            If sOrphModel = "" Then Continue For
            If oOrphanSeen.Contains(sOrphModel) Then Continue For
            oOrphanSeen.Add(sOrphModel)
            If oActualMap.ContainsKey(sOrphModel) Then Continue For
            ' Skip Content Centre / library
            If sOrphModel.ToUpper().Contains("CONTENT CENTER") OrElse sOrphModel.ToUpper().Contains("\LIBRARY\") _
                OrElse Not IsSameOrUnderDirectory(sOrphModel, sOldProjectRoot) _
                OrElse System.Text.RegularExpressions.Regex.IsMatch(System.IO.Path.GetFileNameWithoutExtension(sOrphModel), _
                    "^JC[0-9]+$", System.Text.RegularExpressions.RegexOptions.IgnoreCase) Then
                Try : System.IO.File.AppendAllText(sLogPath, "ORPHAN-SKIP-CC: " & System.IO.Path.GetFileName(sOrphModel) & vbCrLf) : Catch : End Try
                Continue For
            End If
            sOrphNew = ComputeNewName(sOrphModel, sOldProjectRoot, sNewPrefix, sTargetFolder)
            If sOrphNew = "" Then Continue For
            If System.IO.File.Exists(sOrphNew) Then
                oActualMap(sOrphModel) = sOrphNew
                Try : System.IO.File.AppendAllText(sLogPath, "ORPHAN-REUSE: " & System.IO.Path.GetFileName(sOrphModel) & " -> " & System.IO.Path.GetFileName(sOrphNew) & vbCrLf) : Catch : End Try
                Continue For
            End If
            ' v2.2.25: resolve source path — stored path may be vault-relative or not on disk.
            ' Try 1: path as-is.  Try 2: Vault FileManager lookup (Vault-aware, works when
            ' the file is in the vault workspace even if not checked out locally).
            Dim sOrphResolved As String = sOrphModel
            If Not System.IO.File.Exists(sOrphResolved) Then
                Try
                    Dim sVaultFound As String = ThisApplication.FileManager.FindFile(System.IO.Path.GetFileName(sOrphModel))
                    If sVaultFound <> "" AndAlso System.IO.File.Exists(sVaultFound) Then
                        sOrphResolved = sVaultFound
                        Try : System.IO.File.AppendAllText(sLogPath, "ORPHAN-RESOLVED: " & System.IO.Path.GetFileName(sOrphModel) & " -> " & sVaultFound & vbCrLf) : Catch : End Try
                    End If
                Catch
                End Try
            End If
            If Not System.IO.File.Exists(sOrphResolved) Then
                Try : System.IO.File.AppendAllText(sLogPath, "ORPHAN-NOT-ON-DISK: " & System.IO.Path.GetFileName(sOrphModel) & " — not found on disk; check out from Vault first." & vbCrLf) : Catch : End Try
                Continue For
            End If
            Try : System.IO.File.AppendAllText(sLogPath, "ORPHAN: " & System.IO.Path.GetFileName(sOrphModel) & " (drawing-only, not in GA)" & vbCrLf) : Catch : End Try
            oOrphDoc = Nothing
            Try
                ' v2.2.25: check if already open in session (Vault loads refs when drawing opens)
                Try : oOrphDoc = ThisApplication.Documents.ItemByName(sOrphResolved) : Catch : End Try
                If oOrphDoc Is Nothing Then
                    oOrphDoc = ThisApplication.Documents.Open(sOrphResolved, False)
                End If

                ' v2.2.27: .iam orphans get a full WalkTree + Phase-2/3 sub-tree copy so all
                ' child parts come across with the new prefix, refs are fixed inside the new
                ' assembly, and the drawing relink can then point to the correct new copies.
                ' .ipt orphans have no sub-tree so a single SaveAs is still correct.
                Dim sOrphTopExt As String = System.IO.Path.GetExtension(sOrphResolved).ToUpper()
                If sOrphTopExt = ".IAM" Then
                    Dim oOrphEmptyOverrides As New System.Collections.Generic.Dictionary(Of String, String)( _
                        StringComparer.OrdinalIgnoreCase)
                    ProcessOrphanSubTree(oOrphDoc, sOrphModel, sOrphResolved, _
                                         sOldProjectRoot, sNewPrefix, sTargetFolder, _
                                         oActualMap, oStringRules, oOrphEmptyOverrides, sLogPath)
                    If oActualMap.ContainsKey(sOrphModel) Then iOrphCount += 1
                Else
                    ' Single-file part — simple SaveAs + provenance
                    oOrphDoc.SaveAs(sOrphNew, True)
                    If Not System.IO.File.Exists(sOrphNew) Then Throw New System.Exception("SaveAs did not create orphan part")
                    Dim oOrphPartCopy As Document = Nothing
                    Try
                        oOrphPartCopy = ThisApplication.Documents.Open(sOrphNew, False)
                        SetSweeperCopyProperty(oOrphPartCopy, "CS_SourcePath", sOrphModel)
                        SetSweeperCopyProperty(oOrphPartCopy, "CS_CopyProject", sNewPrefix)
                        SetSweeperCopyProperty(oOrphPartCopy, "CS_CopyDate", Now.ToString("yyyy-MM-dd"))
                        oOrphPartCopy.Save2(False)
                    Finally
                        If oOrphPartCopy IsNot Nothing Then
                            Try : oOrphPartCopy.Close(True) : Catch : End Try
                        End If
                    End Try
                    oActualMap(sOrphModel) = sOrphNew
                    iOrphCount += 1
                    Try : System.IO.File.AppendAllText(sLogPath, "ORPHAN-COPY: " & System.IO.Path.GetFileName(sOrphModel) & " -> " & System.IO.Path.GetFileName(sOrphNew) & vbCrLf) : Catch : End Try
                End If
            Catch exOrph As Exception
                Try : System.IO.File.AppendAllText(sLogPath, "ORPHAN-FAIL: " & System.IO.Path.GetFileName(sOrphModel) & " — " & exOrph.Message & vbCrLf) : Catch : End Try
            End Try
            ' Note: do NOT close oOrphDoc here — it may be held open by the drawing in
            ' Inventor's session.  oProvRebuildOpened / F1 Finally handles cleanup.
        Next
    Next
    Try : System.IO.File.AppendAllText(sLogPath, "ORPHAN: " & iOrphCount.ToString() & " copied" & vbCrLf) : Catch : End Try

    ' ── DRAWING RELINK (v2.2.23: ReferencedDocumentDescriptors) ──
    ' Repoints each listed drawing's model references to the new paths using
    ' oActualMap, saves with Save2(False) when a ref was replaced, closes only
    ' if opened here.  The entry drawing is always included.  Which drawings
    ' are opened is unchanged.
    If bFromDwg AndAlso sDwgEntryPath <> "" Then
        Try : System.IO.File.AppendAllText(sLogPath, vbCrLf & "=== DRAWING RELINK ===" & vbCrLf) : Catch : End Try
        ' Suppress iLogic event-driven rule popups and Inventor dialogs during drawing relink.
        ' SilentOperation was restored by F1 Finally after Phase 3 — re-enable both here.
        Dim bRelinkSilent As Boolean = ThisApplication.SilentOperation
        ThisApplication.SilentOperation = True
        Try : ThisApplication.iLogicVb.EventRuleManager.DisableEventRules = True : Catch : End Try
        Dim oRelinkDwgs As New System.Collections.Generic.List(Of String)(oDwgList)
        Dim bRelinkHasEntry As Boolean = False
        Dim sRelinkDwg As String
        For Each sRelinkDwg In oRelinkDwgs
            If String.Equals(sRelinkDwg, sDwgEntryPath, StringComparison.OrdinalIgnoreCase) Then bRelinkHasEntry = True
        Next
        If Not bRelinkHasEntry Then oRelinkDwgs.Insert(0, sDwgEntryPath)
        Dim oDwgR As Document
        Dim bDwgOpenedHere As Boolean
        Dim iDwgReplaced As Integer
        Dim sDwgOld As String
        Dim sDwgNew As String
        Dim sRelinkName As String
        ' v2.2.23: snapshot ReferencedDocumentDescriptors (late-bound Object) before
        ' iterating so ReplaceReference cannot fault the live COM collection, and
        ' so we never cast to Inventor.FileDescriptor.
        Dim oDwgDDs As New System.Collections.Generic.List(Of Object)()
        Dim oDwgDDSnap As Object
        Dim oDwgDD As Object
        Dim oDwgRefFD As Object
        Dim iDwgLt As Integer
        Dim bDwgSaved As Boolean
        Dim iDwgTotal As Integer = 0
        For Each sRelinkDwg In oRelinkDwgs
            oDwgR = Nothing
            bDwgOpenedHere = False
            iDwgReplaced = 0
            bDwgSaved = False
            oDwgDDs.Clear()
            sRelinkName = System.IO.Path.GetFileName(sRelinkDwg)
            Try
                Try
                    oDwgR = ThisApplication.Documents.ItemByName(sRelinkDwg)
                Catch
                End Try
                If oDwgR Is Nothing Then
                    Try
                        oDwgR = ThisApplication.Documents.Open(sRelinkDwg, False)
                        bDwgOpenedHere = True
                        If oDwgR IsNot Nothing Then oProvRebuildOpened.Add(oDwgR)  ' FIX E: F1 Finally closes on failure
                    Catch exDwgOpen As Exception
                        Try : System.IO.File.AppendAllText(sLogPath, "DWG-OPEN-FAIL: " & sRelinkName & " — " & exDwgOpen.Message & vbCrLf) : Catch : End Try
                    End Try
                End If
                If oDwgR IsNot Nothing Then
                    Try
                        For Each oDwgDDSnap In oDwgR.ReferencedDocumentDescriptors
                            oDwgDDs.Add(oDwgDDSnap)
                        Next
                    Catch : End Try
                    For Each oDwgDD In oDwgDDs
                        sDwgOld = ""
                        Try
                            sDwgOld = CStr(oDwgDD.FullDocumentName)
                        Catch
                        End Try
                        If sDwgOld Is Nothing Then
                            sDwgOld = ""
                        End If
                        iDwgLt = sDwgOld.IndexOf("<")
                        If iDwgLt >= 0 Then
                            sDwgOld = sDwgOld.Substring(0, iDwgLt).Trim()
                        End If
                        If sDwgOld = "" Then Continue For
                        If Not oActualMap.ContainsKey(sDwgOld) Then Continue For
                        sDwgNew = oActualMap(sDwgOld)
                        If Not System.IO.File.Exists(sDwgNew) Then Continue For
                        Try
                            oDwgRefFD = oDwgDD.ReferencedFileDescriptor
                            oDwgRefFD.ReplaceReference(sDwgNew)
                            iDwgReplaced += 1
                            Try : System.IO.File.AppendAllText(sLogPath, "DWG-REPLACE: [" & sRelinkName & "] " & System.IO.Path.GetFileName(sDwgOld) & " -> " & System.IO.Path.GetFileName(sDwgNew) & vbCrLf) : Catch : End Try
                        Catch exDwgRep As Exception
                            Try : System.IO.File.AppendAllText(sLogPath, "DWG-REPLACE-FAIL: [" & sRelinkName & "] " & System.IO.Path.GetFileName(sDwgOld) & " — " & exDwgRep.Message & vbCrLf) : Catch : End Try
                        End Try
                    Next
                    ' ── Phase B2: model state re-assertion ───────────────────
                    ' After ReplaceReference the new doc is bound but named
                    ' DrawingView model states (e.g. "Weldment", "LOD_Low") may
                    ' not auto-transfer.  Walk every view and call ChangeModelState
                    ' to re-assert the state it had before relinking.
                    ' Only runs when the user ticked "Match model states?" for this
                    ' drawing AND at least one reference was replaced.
                    Dim bDoStateMatch As Boolean = False
                    oDrawingStateMatch.TryGetValue(sRelinkDwg, bDoStateMatch)
                    If bDoStateMatch AndAlso iDwgReplaced > 0 Then
                        Try
                            Dim oDrawDoc As DrawingDocument = TryCast(oDwgR, DrawingDocument)
                            If oDrawDoc IsNot Nothing Then
                                For Each oSht As Sheet In oDrawDoc.Sheets
                                    For Each oVw As DrawingView In oSht.DrawingViews
                                        Dim sStateName As String = ""
                                        Try : sStateName = oVw.ModelState : Catch : End Try
                                        If Trim(sStateName) <> "" AndAlso String.Compare(sStateName, "Master", True) <> 0 Then
                                            Try
                                                oVw.ChangeModelState(sStateName)
                                                Try : System.IO.File.AppendAllText(sLogPath, "DWG-STATE-OK: " & sRelinkName & " view state re-asserted: " & sStateName & vbCrLf) : Catch : End Try
                                            Catch exState As Exception
                                                Try : System.IO.File.AppendAllText(sLogPath, "DWG-STATE-WARN: " & sRelinkName & " view '" & sStateName & "' re-assert failed: " & exState.Message & vbCrLf) : Catch : End Try
                                            End Try
                                        End If
                                    Next
                                Next
                            End If
                        Catch exStateOuter As Exception
                            Try : System.IO.File.AppendAllText(sLogPath, "DWG-STATE-ERR: " & sRelinkName & " — " & exStateOuter.Message & vbCrLf) : Catch : End Try
                        End Try
                    ElseIf Not bDoStateMatch Then
                        Try : System.IO.File.AppendAllText(sLogPath, "DWG-STATE-SKIP: " & sRelinkName & " (match model states not enabled)" & vbCrLf) : Catch : End Try
                    End If

                    If iDwgReplaced > 0 Then
                        Try
                            oDwgR.Save2(False)
                            bDwgSaved = True
                            Try : System.IO.File.AppendAllText(sLogPath, "DWG-SAVED: " & sRelinkName & vbCrLf) : Catch : End Try
                        Catch exDwgSave As Exception
                            Try : System.IO.File.AppendAllText(sLogPath, "DWG-SAVE-FAIL: " & sRelinkName & " — " & exDwgSave.Message & vbCrLf) : Catch : End Try
                        End Try
                    Else
                        bDwgSaved = True
                    End If
                    iDwgTotal += iDwgReplaced
                    Try : System.IO.File.AppendAllText(sLogPath, "DWG-RELINK: " & sRelinkName & " " & iDwgReplaced & " replaced" & vbCrLf) : Catch : End Try
                    If bDwgOpenedHere AndAlso bDwgSaved Then
                        Try : oDwgR.Close(True) : Catch : End Try
                    End If
                End If
            Catch exDwg As Exception
                Try : System.IO.File.AppendAllText(sLogPath, "DWG-RELINK-ERROR: " & sRelinkName & " — " & exDwg.Message & vbCrLf) : Catch : End Try
            End Try
        Next
        Try : System.IO.File.AppendAllText(sLogPath, "Drawing relink complete: " & oRelinkDwgs.Count & " drawing(s), " & iDwgTotal & " ref(s) replaced." & vbCrLf) : Catch : End Try
        ' Restore SilentOperation and re-enable iLogic event rules.
        Try : ThisApplication.iLogicVb.EventRuleManager.DisableEventRules = False : Catch : End Try
        ThisApplication.SilentOperation = bRelinkSilent
    End If

    ' BBn urgent test: metadata only, after model/drawing reference operations.
    Dim iMetaModel As Integer = 0
    Dim iMetaDwg As Integer = 0
    Dim iMetaFail As Integer = 0
    RunCopiedProjectMetadataPass(sTargetFolder, sOldPrefix, sNewPrefix, oActualMap, _
        oDwgList, sDwgEntryPath, bFromDwg, sLogPath, iMetaModel, iMetaDwg, iMetaFail)

    ' ── 8. Final summary ──────────────────────────────────────────────────────
    Dim sSummary As String = _
        "SUPER CLEAN SWEEPER v2.2.32-META-TEST2 — COMPLETE" & vbCrLf & vbCrLf & _
        "Phase 1  Rename map built:   " & oRenameMap.Count & " file(s)" & vbCrLf & _
        "Phase 2  SaveAs + Provenance:" & vbCrLf & _
        "         Saved    : " & iSaved & vbCrLf & _
        "         Skipped  : " & iSkipped & "  (provenance guard — already processed)" & vbCrLf & _
        "         No-Prov  : " & iNoProvenance & "  (saved but provenance not written — check log)" & vbCrLf & _
        "         Failed   : " & iSaveFailed & vbCrLf & _
        "Phase 3  Ref fix  :" & vbCrLf & _
        "         Fixed    : " & iRefFixed & vbCrLf & _
        "         Failed   : " & iRefFailed & vbCrLf & vbCrLf & _
        "New files in : " & sTargetFolder & vbCrLf & _
        "Log          : " & sLogPath & vbCrLf & vbCrLf & _
        "NEXT STEPS" & vbCrLf & _
        "1. Open the new GA from the target folder to verify the assembly tree." & vbCrLf & _
        "2. Run the Drawing Relink pass to update drawings to new model paths" & vbCrLf & _
        "   (uses CS_ModelRefs + CS_SourcePath matching — no preset map needed)." & vbCrLf & _
        "3. Check the log for SAVEAS-FAIL, SAVED-NO-PROV, or P3-FD-FAIL entries."

    Try : System.IO.File.AppendAllText(sLogPath, vbCrLf & sSummary) : Catch : End Try

    ' ── Refresh Vault browser so the tree shows the new paths without a manual refresh ──
    Try
        ThisApplication.CommandManager.ControlDefinitions.Item("VaultRefresh").Execute()
        Try : System.IO.File.AppendAllText(sLogPath, "Vault browser refreshed." & vbCrLf) : Catch : End Try
    Catch
        Try
            ThisApplication.CommandManager.ControlDefinitions.Item("AppRefreshCmd").Execute()
            Try : System.IO.File.AppendAllText(sLogPath, "AppRefreshCmd executed (VaultRefresh unavailable)." & vbCrLf) : Catch : End Try
        Catch : End Try
    End Try

    ' ── Elapsed time ──
    Dim tsElapsed As TimeSpan = Now - dtStart
    Dim sElapsed As String = String.Format("{0:D2}:{1:D2}:{2:D2}", tsElapsed.Hours, tsElapsed.Minutes, tsElapsed.Seconds)
    Try : System.IO.File.AppendAllText(sLogPath, "Elapsed: " & sElapsed & vbCrLf) : Catch : End Try

    MessageBox.Show(sSummary & vbCrLf & vbCrLf & "Elapsed : " & sElapsed, "Super Clean Sweeper — Complete", _
        MessageBoxButtons.OK, MessageBoxIcon.Information)

End Sub


' ─────────────────────────────────────────────────────────────────────────────
' HELPER: wire TextChanged so a follower box mirrors its master (v2.2.22)
' Each call gets its own parameter bindings — safe for loop use.
' ─────────────────────────────────────────────────────────────────────────────
Sub WireDMTextSync(oMasterBox As System.Windows.Forms.TextBox, _
                   oFollowerBox As System.Windows.Forms.TextBox)
    AddHandler oMasterBox.TextChanged, Sub(sender As Object, E As System.EventArgs) oFollowerBox.Text = oMasterBox.Text
End Sub


' ─────────────────────────────────────────────────────────────────────────────
' HELPER: "Include ALL drawings" toggles every per-drawing include checkbox
' ─────────────────────────────────────────────────────────────────────────────
Sub WireDMIncludeAll(oGlobalChk As System.Windows.Forms.CheckBox, _
                     oIncludeMap As System.Collections.Generic.Dictionary(Of String, System.Windows.Forms.CheckBox))
    AddHandler oGlobalChk.CheckedChanged, Sub(sender As Object, e As System.EventArgs) ApplyDMIncludeAll(oGlobalChk.Checked, oIncludeMap)
End Sub


' ─────────────────────────────────────────────────────────────────────────────
' HELPER: apply Include-ALL state to every per-drawing checkbox (v2.2.22)
' ─────────────────────────────────────────────────────────────────────────────
Sub ApplyDMIncludeAll(bChecked As Boolean, _
                      oIncludeMap As System.Collections.Generic.Dictionary(Of String, System.Windows.Forms.CheckBox))
    Dim oDMMapChk As System.Windows.Forms.CheckBox
    For Each oDMMapChk In oIncludeMap.Values
        oDMMapChk.Checked = bChecked
    Next
End Sub


' ─────────────────────────────────────────────────────────────────────────────
' HELPER: detect anomalous middle-token Find/Replace suggestions (v2.2.22)
' Port of Traverse ShowCopyDesignConfigForm auto-detect.  Walks AllOccurrences
' plus the GA folder; flags mismatched middles (xx, equipment mismatch,
' double-prefix).  Double-prefix patterns are prioritised.  Drops the plain
' old-prefix -> new-prefix swap.  Returns up to iMax {find, replace} pairs.
' ─────────────────────────────────────────────────────────────────────────────
Function DetectStringAnomalies(oAsmDoc As AssemblyDocument, _
                               sOldPrefix As String, _
                               sNewPrefix As String, _
                               iMax As Integer) As System.Collections.Generic.List(Of String())
    Dim oResult As New System.Collections.Generic.List(Of String())()
    If oAsmDoc Is Nothing Then Return oResult
    If iMax < 1 Then Return oResult

    Dim oPathsToScan As New System.Collections.Generic.HashSet(Of String)(StringComparer.OrdinalIgnoreCase)
    Dim sSourceAsmPath As String = ""
    Try
        sSourceAsmPath = oAsmDoc.FullFileName
    Catch
        sSourceAsmPath = ""
    End Try
    If sSourceAsmPath <> "" Then oPathsToScan.Add(sSourceAsmPath)

    ' Full-tree paths via AllOccurrences (same as old Traverse rule)
    Dim oSROcc As ComponentOccurrence
    Dim sOccPath As String
    Try
        For Each oSROcc In oAsmDoc.ComponentDefinition.AllOccurrences
            sOccPath = ""
            Try
                sOccPath = oSROcc.ReferencedFileDescriptor.FullDocumentName
            Catch
            End Try
            If Trim(sOccPath) <> "" AndAlso Not sOccPath.Contains("*") Then
                oPathsToScan.Add(sOccPath)
            End If
        Next
    Catch
        ' Fallback: AllLeafOccurrences if AllOccurrences is unavailable
        Try
            For Each oSROcc In oAsmDoc.ComponentDefinition.Occurrences.AllLeafOccurrences
                sOccPath = ""
                Try
                    sOccPath = oSROcc.ReferencedFileDescriptor.FullDocumentName
                Catch
                    Try
                        sOccPath = oSROcc.Definition.Document.FullFileName
                    Catch
                    End Try
                End Try
                If Trim(sOccPath) <> "" AndAlso Not sOccPath.Contains("*") Then
                    oPathsToScan.Add(sOccPath)
                End If
            Next
        Catch
        End Try
    End Try

    ' Also include immediate GA folder (fallback / drawings)
    Dim sSourceFolder As String = ""
    Dim sFilePath As String
    Dim sExt As String
    If sSourceAsmPath <> "" AndAlso System.IO.File.Exists(sSourceAsmPath) Then
        sSourceFolder = System.IO.Path.GetDirectoryName(sSourceAsmPath)
        Try
            For Each sFilePath In System.IO.Directory.GetFiles(sSourceFolder, "*.*")
                sExt = System.IO.Path.GetExtension(sFilePath).ToLower()
                If sExt = ".ipt" OrElse sExt = ".iam" OrElse sExt = ".idw" OrElse sExt = ".dwg" Then
                    oPathsToScan.Add(sFilePath)
                End If
            Next
        Catch
        End Try
    End If

    Dim sGABase As String = ""
    Dim sCanonMiddle As String = ""
    Dim iFirstDash As Integer
    Dim iFirstV As Integer
    If sSourceAsmPath <> "" AndAlso System.IO.File.Exists(sSourceAsmPath) Then
        sGABase = System.IO.Path.GetFileNameWithoutExtension(sSourceAsmPath)
        iFirstDash = sGABase.IndexOf("-"c)
        iFirstV = sGABase.ToUpper().IndexOf("V")
        If iFirstDash > 0 AndAlso iFirstV > iFirstDash Then
            sCanonMiddle = sGABase.Substring(iFirstDash, iFirstV - iFirstDash)
            If Not sCanonMiddle.EndsWith("-") Then sCanonMiddle = sCanonMiddle & "-"
        End If
    End If

    Dim oMiddleCounts As New System.Collections.Generic.Dictionary(Of String, Integer)(StringComparer.OrdinalIgnoreCase)
    Dim sBase As String
    Dim sBaseUp As String
    Dim iDash As Integer
    Dim iV As Integer
    Dim sMiddle As String
    Dim sMidTrim As String
    Dim bLooksLikeConvention As Boolean
    Dim bFlag As Boolean
    Dim sCanonEq As String
    Dim sMidEq As String
    Dim sCanonParts() As String
    Dim sMidParts() As String
    For Each sFilePath In oPathsToScan
        sBase = System.IO.Path.GetFileNameWithoutExtension(sFilePath)
        sBaseUp = sBase.ToUpper()
        If Not sBaseUp.StartsWith("PJ") Then Continue For
        If sBaseUp.Contains("GAL") OrElse sBaseUp.Contains("AS 11") OrElse _
           sBaseUp.Contains("AS 12") OrElse sBaseUp.Contains("DIN ") OrElse _
           sBaseUp.Contains("ISO ") OrElse sBaseUp.Contains("WASHER") OrElse _
           sBaseUp.Contains("NYLOCK") OrElse sBaseUp.Contains("SHACKLE") Then Continue For
        iDash = sBase.IndexOf("-"c)
        iV = sBaseUp.IndexOf("V")
        If iDash < 1 OrElse iV <= iDash Then Continue For
        sMiddle = sBase.Substring(iDash, iV - iDash)
        If Not sMiddle.EndsWith("-") Then sMiddle = sMiddle & "-"
        If sCanonMiddle <> "" AndAlso String.Compare(sMiddle, sCanonMiddle, True) = 0 Then Continue For
        If sMiddle.Length < 3 Then Continue For
        sMidTrim = sMiddle.Trim("-"c)
        bLooksLikeConvention = False
        If sMidTrim.Length > 0 AndAlso Char.IsDigit(sMidTrim(0)) Then bLooksLikeConvention = True
        If sMiddle.ToUpper().Contains("XX") Then bLooksLikeConvention = True
        If sMiddle.ToUpper().Contains("-PJ") OrElse sMiddle.ToUpper().StartsWith("PJ") Then bLooksLikeConvention = True
        If Not bLooksLikeConvention Then Continue For
        bFlag = False
        If sMiddle.ToUpper().Contains("XX") Then
            bFlag = True
        ElseIf sCanonMiddle <> "" Then
            sCanonEq = ""
            sMidEq = ""
            sCanonParts = sCanonMiddle.Trim("-"c).Split("-"c)
            sMidParts = sMiddle.Trim("-"c).Split("-"c)
            If sCanonParts.Length > 0 Then sCanonEq = sCanonParts(0)
            If sMidParts.Length > 0 Then sMidEq = sMidParts(0)
            If sCanonEq <> "" AndAlso String.Compare(sMidEq, sCanonEq, True) <> 0 Then
                bFlag = True
            ElseIf sMiddle.ToUpper().Contains("-PJ") OrElse sMiddle.ToUpper().StartsWith("PJ") Then
                bFlag = True
            End If
        End If
        If Not bFlag Then Continue For
        If oMiddleCounts.ContainsKey(sMiddle) Then
            oMiddleCounts(sMiddle) = oMiddleCounts(sMiddle) + 1
        Else
            oMiddleCounts(sMiddle) = 1
        End If
    Next

    Dim oSorted As New System.Collections.Generic.List(Of System.Collections.Generic.KeyValuePair(Of String, Integer))
    Dim oMidKV As System.Collections.Generic.KeyValuePair(Of String, Integer)
    For Each oMidKV In oMiddleCounts
        oSorted.Add(oMidKV)
    Next
    oSorted.Sort(Function(a As System.Collections.Generic.KeyValuePair(Of String, Integer), _
                          b As System.Collections.Generic.KeyValuePair(Of String, Integer)) As Integer
                     Dim aDbl As Boolean = a.Key.ToUpper().Contains("-PJ") OrElse a.Key.ToUpper().StartsWith("PJ")
                     Dim bDbl As Boolean = b.Key.ToUpper().Contains("-PJ") OrElse b.Key.ToUpper().StartsWith("PJ")
                     If aDbl <> bDbl Then Return If(aDbl, -1, 1)
                     Return b.Value.CompareTo(a.Value)
                 End Function)

    Dim oSeenTokens As New System.Collections.Generic.HashSet(Of String)(StringComparer.OrdinalIgnoreCase)
    Dim iAdded As Integer = 0
    Dim sFindTok As String
    Dim sReplTok As String
    For Each oMidKV In oSorted
        If iAdded >= iMax Then Exit For
        If sCanonMiddle = "" Then Exit For
        sFindTok = oMidKV.Key
        sReplTok = sCanonMiddle
        If String.Compare(Trim(sFindTok), sOldPrefix, True) = 0 AndAlso _
           String.Compare(Trim(sReplTok), sNewPrefix, True) = 0 Then
            Continue For
        End If
        If Not oSeenTokens.Contains(sFindTok) Then
            oSeenTokens.Add(sFindTok)
            oResult.Add(New String() {sFindTok, sReplTok})
            iAdded = iAdded + 1
        End If
    Next
    Return oResult
End Function


' ─────────────────────────────────────────────────────────────────────────────
' HELPER: Compute new full path for a file
' Returns "" if file is NOT under sOldProjectRoot (Content Centre etc.)
' Smart rename: strip any existing PJ-style "PJXXXXX-" prefix from basename
' before prepending sNewPrefix.  Non-prefixed files get prefix prepended.
' ─────────────────────────────────────────────────────────────────────────────
Function IsSameOrUnderDirectory(sCandidatePath As String, sDirectoryPath As String) As Boolean
    If String.IsNullOrWhiteSpace(sCandidatePath) OrElse String.IsNullOrWhiteSpace(sDirectoryPath) Then Return False
    Try
        If Not System.IO.Path.IsPathRooted(sCandidatePath) OrElse _
           Not System.IO.Path.IsPathRooted(sDirectoryPath) Then Return False

        Dim sCandidateFull As String = System.IO.Path.GetFullPath(sCandidatePath)
        Dim sDirectoryFull As String = System.IO.Path.GetFullPath(sDirectoryPath)
        Dim sCandidateRoot As String = System.IO.Path.GetPathRoot(sCandidateFull)
        Dim sDirectoryRoot As String = System.IO.Path.GetPathRoot(sDirectoryFull)
        While sCandidateFull.Length > sCandidateRoot.Length AndAlso _
              (sCandidateFull.EndsWith(System.IO.Path.DirectorySeparatorChar.ToString(), StringComparison.Ordinal) OrElse _
               sCandidateFull.EndsWith(System.IO.Path.AltDirectorySeparatorChar.ToString(), StringComparison.Ordinal))
            sCandidateFull = sCandidateFull.Substring(0, sCandidateFull.Length - 1)
        End While
        While sDirectoryFull.Length > sDirectoryRoot.Length AndAlso _
              (sDirectoryFull.EndsWith(System.IO.Path.DirectorySeparatorChar.ToString(), StringComparison.Ordinal) OrElse _
               sDirectoryFull.EndsWith(System.IO.Path.AltDirectorySeparatorChar.ToString(), StringComparison.Ordinal))
            sDirectoryFull = sDirectoryFull.Substring(0, sDirectoryFull.Length - 1)
        End While

        If String.Equals(sCandidateFull, sDirectoryFull, StringComparison.OrdinalIgnoreCase) Then Return True
        Dim sDirectoryPrefix As String = sDirectoryFull
        If Not sDirectoryPrefix.EndsWith(System.IO.Path.DirectorySeparatorChar.ToString(), StringComparison.Ordinal) AndAlso _
           Not sDirectoryPrefix.EndsWith(System.IO.Path.AltDirectorySeparatorChar.ToString(), StringComparison.Ordinal) Then
            sDirectoryPrefix &= System.IO.Path.DirectorySeparatorChar
        End If
        Return sCandidateFull.StartsWith(sDirectoryPrefix, StringComparison.OrdinalIgnoreCase)
    Catch
        Return False
    End Try
End Function

' ─────────────────────────────────────────────────────────────────────────────
' HELPER: CC guard — returns True only for parts in the TOP-LEVEL Vault
' Content Center folder (not project-local CC subfolders).
' A path like C:\Vault\Projects\PJ00193\Content Center Files\... is a
' non-standard part saved in the project's own CC subfolder and must be COPIED.
' A path like C:\Vault\Content Center Files\... is a true CC library part
' and must be SKIPPED.
' v2.2.35 — replaces the old sPath.Contains("CONTENT CENTER") guard.
' ─────────────────────────────────────────────────────────────────────────────
Function IsTopLevelContentCenter(sPath As String) As Boolean
    Dim sUp As String = sPath.ToUpper()
    Dim iCC As Integer = sUp.IndexOf("\CONTENT CENTER FILES\")
    If iCC < 0 Then Return False
    Dim iProj As Integer = sUp.IndexOf("\PROJECTS\")
    If iProj >= 0 AndAlso iProj < iCC Then Return False
    Return True
End Function

Function ComputeNewName(sOldFull As String, _
                         sOldProjectRoot As String, _
                         sNewPrefix As String, _
                         sTargetFolder As String) As String
    ' Never copy parts that live in the top-level Vault Content Center folder.
    ' Parts in a project-local Content Center subfolder ARE copied (non-std parts).
    If IsTopLevelContentCenter(sOldFull) Then Return ""
    ' TEST2 fail-closed: only copy sources within the selected old project root.
    ' This blocks shared JC and other Vault library parts outside that root.
    If Not IsSameOrUnderDirectory(sOldFull, sOldProjectRoot) Then Return ""
    ' Also block JC-prefixed library source names until their provenance is reviewed.
    If System.Text.RegularExpressions.Regex.IsMatch(System.IO.Path.GetFileNameWithoutExtension(sOldFull), _
        "^JC[0-9]+$", System.Text.RegularExpressions.RegexOptions.IgnoreCase) Then Return ""
    ' Skip files already in the target folder (already processed on a prior run)
    If IsSameOrUnderDirectory(sOldFull, sTargetFolder) Then Return ""

    Dim sBase As String = System.IO.Path.GetFileNameWithoutExtension(sOldFull)
    Dim sExt  As String = System.IO.Path.GetExtension(sOldFull)

    ' Strip existing PJ-style prefix if present AND old ≠ new prefix.
    ' When old = new prefix (rerun / cleanup pass), keep the basename as-is so
    ' files already correctly named don't get double-prefixed.
    ' A PJ-style prefix: token before first "-" starts with "PJ", all alphanumeric.
    ' E.g. "PJ00161-E3432-8-HANDRAIL" → strip "PJ00161-" → "E3432-8-HANDRAIL"
    '      "JC002702" or "AS 1111 - M16" → no PJ prefix → keep whole basename
    Dim sStrippedBase As String = sBase
    If String.Compare(sOldProjectRoot, "", True) <> 0 Then  ' always true; used as scope guard
        Dim iFirstDash As Integer = sBase.IndexOf("-"c)
        If iFirstDash > 0 Then
            Dim sToken0 As String = sBase.Substring(0, iFirstDash).Trim()
            ' Only strip if token0 starts with "PJ", is all alphanumeric,
            ' AND the token does NOT equal sNewPrefix (avoid stripping when same prefix)
            If sToken0.ToUpper().StartsWith("PJ") AndAlso _
               String.Compare(sToken0, sNewPrefix, True) <> 0 Then
                Dim bAllAlNum As Boolean = True
                Dim ci As Integer
                For ci = 0 To sToken0.Length - 1
                    If Not Char.IsLetterOrDigit(sToken0(ci)) Then
                        bAllAlNum = False
                        Exit For
                    End If
                Next ci
                If bAllAlNum Then
                    Dim sAfterFirstToken As String = sBase.Substring(iFirstDash + 1)
                    If sAfterFirstToken.Length > 0 Then
                        sStrippedBase = sAfterFirstToken
                    End If
                End If
            End If
        End If
    End If

    ' Prepend new prefix: "PJ00222-E3432-8-HANDRAIL" or "PJ00222-JC002702" etc.
    ' If old=new prefix and basename already starts with sNewPrefix, keep as-is
    ' (the file is already correctly named; copy it flat to target).
    Dim sNewBase As String
    If sBase.ToUpper().StartsWith(sNewPrefix.ToUpper() & "-") Then
        ' Already has the right prefix — keep the filename unchanged
        sNewBase = sBase
    Else
        sNewBase = sNewPrefix & "-" & sStrippedBase
    End If

    Dim sNewFull As String = System.IO.Path.Combine(sTargetFolder, sNewBase & sExt)

    ' Final guard: if source and destination are identical paths, nothing to do
    If String.Compare(sOldFull, sNewFull, True) = 0 Then Return ""

    Return sNewFull
End Function


' ─────────────────────────────────────────────────────────────────────────────
' HELPER: Write 8-property delta-provenance chain to a document
' Call AFTER the document has been SaveAs'd to its new path and is open.
' ─────────────────────────────────────────────────────────────────────────────
Sub WriteProvenanceProps(oDoc As Document, _
                          sOldPath As String, _
                          sNewProject As String, _
                          sOldGUID As String, _
                          sRootSource As String, _
                          sRootGUID As String, _
                          iRunCount As Integer, _
                          sLogPath As String)
    Try
        Dim oUDP As PropertySet = oDoc.PropertySets("Inventor User Defined Properties")
        Dim aNames(7) As String
        Dim aVals(7)  As String
        aNames(0) = "CS_SourcePath"  : aVals(0) = sOldPath
        aNames(1) = "CS_SourceName"  : aVals(1) = System.IO.Path.GetFileName(sOldPath)
        aNames(2) = "CS_CopyProject" : aVals(2) = sNewProject
        aNames(3) = "CS_CopyDate"    : aVals(3) = Now.ToString("yyyy-MM-dd")
        aNames(4) = "CS_SourceGUID"  : aVals(4) = sOldGUID
        aNames(5) = "CS_RootSource"  : aVals(5) = sRootSource
        aNames(6) = "CS_RootGUID"    : aVals(6) = sRootGUID
        aNames(7) = "CS_RunCount"    : aVals(7) = iRunCount.ToString()
        Dim i As Integer
        For i = 0 To 7
            Dim sPropName As String = aNames(i)
            Dim sPropVal  As String = aVals(i)
            Try
                oUDP.Item(sPropName).Value = sPropVal
            Catch
                Try
                    oUDP.Add(sPropVal, sPropName)
                Catch exAdd As Exception
                    Try
                        System.IO.File.AppendAllText(sLogPath, _
                            "PROV-WARN: could not set " & sPropName & _
                            " on " & oDoc.DisplayName & " — " & exAdd.Message & vbCrLf)
                    Catch : End Try
                End Try
            End Try
        Next i
    Catch ex As Exception
        Try
            System.IO.File.AppendAllText(sLogPath, _
                "PROV-FAIL: " & oDoc.DisplayName & " — " & ex.Message & vbCrLf)
        Catch : End Try
    End Try
End Sub


' ─────────────────────────────────────────────────────────────────────────────
' HELPER: Write CS_ModelRefs to a drawing document
' Writes pipe-delimited list of old model paths the drawing referenced.
' ─────────────────────────────────────────────────────────────────────────────
Sub WriteDrawingModelRefs(oDwg As Document, _
                           oModelPaths As System.Collections.Generic.List(Of String), _
                           sLogPath As String)
    If oModelPaths Is Nothing Then Return
    If oModelPaths.Count = 0 Then Return
    Dim sJoined As String = String.Join("|", oModelPaths.ToArray())
    Try
        Dim oUDP As PropertySet = oDwg.PropertySets("Inventor User Defined Properties")
        Try
            oUDP.Item("CS_ModelRefs").Value = sJoined
        Catch
            Try
                oUDP.Add(sJoined, "CS_ModelRefs")
            Catch exA As Exception
                Try
                    System.IO.File.AppendAllText(sLogPath, _
                        "MODELREFS-WARN: " & oDwg.DisplayName & " — " & exA.Message & vbCrLf)
                Catch : End Try
            End Try
        End Try
    Catch ex As Exception
        Try
            System.IO.File.AppendAllText(sLogPath, _
                "MODELREFS-FAIL: " & oDwg.DisplayName & " — " & ex.Message & vbCrLf)
        Catch : End Try
    End Try
End Sub


' ─────────────────────────────────────────────────────────────────────────────
' HELPER: Check if destination file was already processed in a prior run
' Returns True only when the destination exists AND carries
' CS_CopyProject = sProject.
' ─────────────────────────────────────────────────────────────────────────────
Function IsAlreadyProcessed(sNewFull As String, sProject As String) As Boolean
    If Not System.IO.File.Exists(sNewFull) Then Return False
    Dim sExisting As String = ""
    Try
        Dim oDoc As Document = Nothing
        Try : oDoc = ThisApplication.Documents.ItemByName(sNewFull) : Catch : End Try
        If oDoc IsNot Nothing Then
            Try
                sExisting = oDoc.PropertySets( _
                    "Inventor User Defined Properties").Item("CS_CopyProject").Value
            Catch : End Try
        Else
            Dim bPrevSilent As Boolean = ThisApplication.SilentOperation
            ThisApplication.SilentOperation = True
            Try
                Dim oTmp As Document = ThisApplication.Documents.Open(sNewFull, False)
                Try
                    sExisting = oTmp.PropertySets( _
                        "Inventor User Defined Properties").Item("CS_CopyProject").Value
                Catch : End Try
                Try : oTmp.Close(True) : Catch : End Try
            Catch
            Finally
                ThisApplication.SilentOperation = bPrevSilent
            End Try
        End If
    Catch : End Try
    Return (String.Compare(sExisting, sProject, True) = 0)
End Function


' ─────────────────────────────────────────────────────────────────────────────
' HELPER: Walk assembly tree and build old->new rename map
' Visits every referenced .iam and .ipt under the old project root.
' ALL files under sOldProjectRoot are included (not just PJ-prefixed ones).
' Content Centre parts are excluded.
'
' FIX 4: oWalkOpened receives every Document opened here (not already in
'   session) so Sub Main can close them before Phase 2 starts, ensuring
'   Phase 2 controls each document's lifecycle with bOpenedHere2.
' FIX 5: oMappedTargets is a HashSet mirror of oRenameMap.Values for O(1)
'   collision lookup (replaces O(n) Dictionary.ContainsValue).
' ─────────────────────────────────────────────────────────────────────────────
Sub WalkTree(oDoc As Document, _
             sOldProjectRoot As String, _
             sNewPrefix As String, _
             sTargetFolder As String, _
             oRenameMap As System.Collections.Generic.Dictionary(Of String, String), _
             oSeen As System.Collections.Generic.HashSet(Of String), _
             sLogPath As String, _
             oMappedTargets As System.Collections.Generic.HashSet(Of String), _
             oWalkOpened As System.Collections.Generic.List(Of Document), _
             oStringRules As System.Collections.Generic.List(Of String()), _
             oReuseKeys As System.Collections.Generic.HashSet(Of String), _
             oSourcePathCache As System.Collections.Generic.Dictionary(Of String, String), _
             oNameOverrides As System.Collections.Generic.Dictionary(Of String, String))

    Dim sFullPath As String = ""
    Try : sFullPath = oDoc.FullFileName : Catch : Return : End Try

    Dim sFullUpper As String = sFullPath.ToUpper()
    If oSeen.Contains(sFullUpper) Then Return
    oSeen.Add(sFullUpper)

    ' ── Recurse into referenced children first (deepest-first) ───────────────
    Try
        For Each oDesc As Object In oDoc.ReferencedDocumentDescriptors
            Dim sRefPath As String = ""
            Try : sRefPath = oDesc.FullDocumentName : Catch : Continue For : End Try

            ' Strip DART SHUT state tag e.g. "C:\path\file.iam<DART SHUT>"
            Dim iAngle As Integer = sRefPath.IndexOf("<"c)
            If iAngle > 0 Then sRefPath = sRefPath.Substring(0, iAngle)
            sRefPath = sRefPath.Trim()
            If sRefPath = "" Then Continue For

            Dim sRefExt As String = System.IO.Path.GetExtension(sRefPath).ToUpper()
            If sRefExt <> ".IAM" AndAlso sRefExt <> ".IPT" Then Continue For
            If Not System.IO.File.Exists(sRefPath) Then Continue For
            If IsTopLevelContentCenter(sRefPath) Then Continue For
            If Not IsSameOrUnderDirectory(sRefPath, sOldProjectRoot) Then
                Try : System.IO.File.AppendAllText(sLogPath, "WALK-EXTERNAL-LIB-SKIP: " & sRefPath & vbCrLf) : Catch : End Try
                Continue For
            End If
            If System.Text.RegularExpressions.Regex.IsMatch(System.IO.Path.GetFileNameWithoutExtension(sRefPath), _
                "^JC[0-9]+$", System.Text.RegularExpressions.RegexOptions.IgnoreCase) Then
                Try : System.IO.File.AppendAllText(sLogPath, "WALK-JC-SKIP: " & sRefPath & vbCrLf) : Catch : End Try
                Continue For
            End If
            If oSeen.Contains(sRefPath.ToUpper()) Then Continue For

            Dim oChild As Document = Nothing
            Dim bWalkOpenedChild As Boolean = False
            Try : oChild = ThisApplication.Documents.ItemByName(sRefPath) : Catch : End Try
            If oChild Is Nothing Then
                Try
                    oChild = ThisApplication.Documents.Open(sRefPath, False)
                    bWalkOpenedChild = True
                    ' FIX 4: Track immediately — before CC guard can Continue For past this line
                    If oChild IsNot Nothing Then oWalkOpened.Add(oChild)
                Catch exOpen As Exception
                    Try
                        System.IO.File.AppendAllText(sLogPath, _
                            "WALK-OPEN-FAIL: " & System.IO.Path.GetFileName(sRefPath) & _
                            " — " & exOpen.Message & vbCrLf)
                    Catch : End Try
                    Continue For
                End Try
            End If

            ' CC guard: skip only when BOTH IsContentMember=True AND the file
            ' actually lives in the Vault Content Center folder.
            ' Non-standard fasteners/parts placed from CC but saved into a
            ' project folder must be copied and prefixed like any project file.
            Try
                If oChild.DocumentType = DocumentTypeEnum.kPartDocumentObject AndAlso _
                   oChild.ComponentDefinition.IsContentMember AndAlso _
                   IsTopLevelContentCenter(sRefPath) Then
                    Try
                        System.IO.File.AppendAllText(sLogPath, _
                            "WALK-CC-SKIP: " & System.IO.Path.GetFileName(sRefPath) & vbCrLf)
                    Catch : End Try
                    Continue For
                End If
            Catch : End Try

            WalkTree(oChild, sOldProjectRoot, sNewPrefix, sTargetFolder, _
                     oRenameMap, oSeen, sLogPath, oMappedTargets, oWalkOpened, _
                     oStringRules, oReuseKeys, oSourcePathCache, oNameOverrides)
        Next
    Catch exWalk As Exception
        Try
            System.IO.File.AppendAllText(sLogPath, _
                "WALK-DESC-FAIL: " & System.IO.Path.GetFileName(sFullPath) & _
                " — " & exWalk.Message & vbCrLf)
        Catch : End Try
    End Try

    ' ── Compute new name for THIS document ───────────────────────────────────
    ' v2: copy any file NOT already in sTargetFolder and NOT Content Centre
    Dim sNewFull As String = ComputeNewName(sFullPath, sOldProjectRoot, sNewPrefix, sTargetFolder)
    If sNewFull = "" Then Return   ' already in target, or CC part
    ' v2.2.19: Drawing List name replaces the automatic new base name
    Dim bNameOverride As Boolean = False
    If oNameOverrides IsNot Nothing AndAlso oNameOverrides.ContainsKey(sFullPath) Then
        sNewFull = System.IO.Path.Combine(System.IO.Path.GetDirectoryName(sNewFull), _
            oNameOverrides(sFullPath) & System.IO.Path.GetExtension(sFullPath))
        bNameOverride = True
    End If

    ' ── Collision guard: use oMappedTargets HashSet for O(1) lookup ──────────
    ' FIX 5: oMappedTargets.Contains replaces O(n) oRenameMap.ContainsValue.
    '        E.g. multiple different "Bolted Connection1.iam" from different
    '        sub-assemblies would otherwise all collapse onto the same target name.
    If Not oRenameMap.ContainsKey(sFullPath) Then
        ' v2.2.15: apply string rules, then reuse / suffix per provenance
        Dim sRuled As String = sNewFull
        If Not bNameOverride Then sRuled = ApplyStringRules(sNewFull, oStringRules)
        Dim bRuleChanged As Boolean = Not String.Equals(sRuled, sNewFull, StringComparison.Ordinal)
        Dim bReused As Boolean = False
        Dim sTestFull As String = ResolveTarget(sFullPath, sRuled, bRuleChanged, oMappedTargets, sLogPath, bReused, oSourcePathCache)
        ' v2.2.17: "" means the suffix range was exhausted — skip this file
        If sTestFull <> "" AndAlso String.Compare(sFullPath, sTestFull, True) <> 0 Then
            oRenameMap(sFullPath) = sTestFull
            oMappedTargets.Add(sTestFull)
            If bReused Then oReuseKeys.Add(sFullPath)
            Try
                System.IO.File.AppendAllText(sLogPath, _
                    "MAP: " & System.IO.Path.GetFileName(sFullPath) & _
                    "  ->  " & System.IO.Path.GetFileName(sTestFull) & vbCrLf)
            Catch : End Try
        End If
    End If
End Sub


' ─────────────────────────────────────────────────────────────────────────────
' HELPER: Phase 4 live occurrence resweep (v2.2.4)
' ─────────────────────────────────────────────────────────────────────────────
Sub Phase4_WalkOccs(oCompDef As ComponentDefinition, _
                    oActualMap As System.Collections.Generic.Dictionary(Of String, String), _
                    oTargetByBase As System.Collections.Generic.Dictionary(Of String, String), _
                    sTargetFolder As String, _
                    sLogPath As String, _
                    oVisited As System.Collections.Generic.HashSet(Of String), _
                    ByRef iFixed As Integer, _
                    ByRef iFailed As Integer)
    Dim sThisFull As String = ""
    Try : sThisFull = oCompDef.Document.FullFileName : Catch : Return : End Try
    If oVisited.Contains(sThisFull.ToUpper()) Then Return
    oVisited.Add(sThisFull.ToUpper())

    ' Snapshot occurrences
    Dim oOccList As New System.Collections.Generic.List(Of ComponentOccurrence)()
    Try
        For Each oOccSnap As ComponentOccurrence In oCompDef.Occurrences
            oOccList.Add(oOccSnap)
        Next
    Catch : End Try

    For Each oOcc As ComponentOccurrence In oOccList
        Dim sOccPath As String = ""
        Try
            sOccPath = oOcc.Definition.Document.FullFileName
        Catch
            Try
                sOccPath = oOcc.ReferencedFileDescriptor.FullFileName
            Catch
            End Try
        End Try
        If sOccPath = "" Then Continue For

        ' Recurse into the child first if it is an assembly. This runs for every
        ' assembly child, including ones already in the target folder, so their
        ' own children still pointing at old paths are swept too. oVisited stops
        ' each assembly being walked more than once.
        Try
            Dim oChildDef As ComponentDefinition = oOcc.Definition
            If oChildDef IsNot Nothing AndAlso oChildDef.Document.DocumentType = DocumentTypeEnum.kAssemblyDocumentObject Then
                Phase4_WalkOccs(oChildDef, oActualMap, oTargetByBase, sTargetFolder, sLogPath, oVisited, iFixed, iFailed)
            End If
        Catch : End Try

        If IsSameOrUnderDirectory(sOccPath, sTargetFolder) Then Continue For

        Dim sNewPath As String = ""
        If oActualMap.ContainsKey(sOccPath) Then
            sNewPath = oActualMap(sOccPath)
        Else
            Dim sBase As String = System.IO.Path.GetFileName(sOccPath)
            If oTargetByBase.ContainsKey(sBase) Then sNewPath = oTargetByBase(sBase)
        End If
        If sNewPath = "" OrElse Not System.IO.File.Exists(sNewPath) Then Continue For
        If String.Compare(sOccPath, sNewPath, True) = 0 Then Continue For

        ' Replace the occurrence
        Dim bWasSuppressed As Boolean = False
        Try : bWasSuppressed = oOcc.Suppressed : Catch : End Try
        If bWasSuppressed Then
            Try : oOcc.Unsuppress() : Catch : End Try
        End If
        Dim bP4Replaced As Boolean = False
        Dim sP4Method As String = "Occurrence.Replace"
        Dim sP4Error As String = ""
        Try
            oOcc.Replace(sNewPath, False)
            bP4Replaced = True
        Catch exRep As Exception
            sP4Error = "Occurrence.Replace HRESULT=0x" & exRep.HResult.ToString("X8") & " " & exRep.Message
            ' Descriptor fallback can succeed when Inventor rejects occurrence replacement.
            Try
                Dim oP4FD As FileDescriptor = oOcc.ReferencedFileDescriptor
                If oP4FD IsNot Nothing Then
                    oP4FD.ReplaceReference(sNewPath)
                    bP4Replaced = True
                    sP4Method = "Descriptor.ReplaceReference"
                End If
            Catch exP4FD As Exception
                sP4Error &= " | Descriptor.ReplaceReference HRESULT=0x" & _
                    exP4FD.HResult.ToString("X8") & " " & exP4FD.Message
            End Try
            ' Third fallback: File.ReferencedFileDescriptors on the parent doc.
            ' Needed for FG frame assemblies whose occurrence FD does not expose
            ' the FileDescriptor COM interface (0x80004002 E_NOINTERFACE).
            If Not bP4Replaced Then
                Try
                    Dim oParentDoc As Document = oCompDef.Document
                    If oParentDoc IsNot Nothing AndAlso oParentDoc.File IsNot Nothing Then
                        For Each oFileFD As Object In oParentDoc.File.ReferencedFileDescriptors
                            Dim sFileFDPath As String = ""
                            Try : sFileFDPath = oFileFD.FullFileName : Catch : Continue For : End Try
                            If String.Equals(sFileFDPath, sOccPath, StringComparison.OrdinalIgnoreCase) Then
                                oFileFD.ReplaceReference(sNewPath)
                                bP4Replaced = True
                                sP4Method = "File.FD.ReplaceReference"
                                Exit For
                            End If
                        Next
                    End If
                Catch exP4File As Exception
                    sP4Error &= " | File.FD.ReplaceReference HRESULT=0x" & _
                        exP4File.HResult.ToString("X8") & " " & exP4File.Message
                End Try
            End If
        End Try
        If bP4Replaced Then
            Dim sP4Resolved As String = ""
            Try : sP4Resolved = oOcc.ReferencedFileDescriptor.FullFileName : Catch : End Try
            If sP4Resolved = "" Then
                Try : sP4Resolved = oOcc.Definition.Document.FullFileName : Catch : End Try
            End If
            If Not String.Equals(sP4Resolved, sNewPath, StringComparison.OrdinalIgnoreCase) Then
                bP4Replaced = False
                sP4Error &= " | VERIFY-MISMATCH: actual=" & sP4Resolved & " expected=" & sNewPath
            End If
        End If
        If bP4Replaced Then
            iFixed += 1
            Try : System.IO.File.AppendAllText(sLogPath, _
                "P4-REPLACE: " & System.IO.Path.GetFileName(sOccPath) & " -> " & _
                System.IO.Path.GetFileName(sNewPath) & " [" & sP4Method & "]" & vbCrLf) : Catch : End Try
        Else
            iFailed += 1
            Try : System.IO.File.AppendAllText(sLogPath, _
                "P4-REPLACE-FAIL: " & sOccPath & " -> " & sNewPath & _
                " [parent=" & sThisFull & "] " & sP4Error & vbCrLf) : Catch : End Try
        End If
        If bWasSuppressed Then
            Try : oOcc.Suppress() : Catch : End Try
        End If
    Next

    ' Save this assembly if it is in the target folder
    If IsSameOrUnderDirectory(sThisFull, sTargetFolder) Then
        Try
            Dim oFA As System.IO.FileAttributes = System.IO.File.GetAttributes(sThisFull)
            If (oFA And System.IO.FileAttributes.ReadOnly) = System.IO.FileAttributes.ReadOnly Then
                System.IO.File.SetAttributes(sThisFull, oFA And Not System.IO.FileAttributes.ReadOnly)
            End If
            Dim oDoc As Document = oCompDef.Document
            oDoc.Save2(False)
            Try : System.IO.File.AppendAllText(sLogPath, "P4-SAVED: " & System.IO.Path.GetFileName(sThisFull) & vbCrLf) : Catch : End Try
        Catch exSave As Exception
            Try : System.IO.File.AppendAllText(sLogPath, "P4-SAVE-FAIL: " & System.IO.Path.GetFileName(sThisFull) & " — " & exSave.Message & vbCrLf) : Catch : End Try
        End Try
    End If
End Sub


' ─────────────────────────────────────────────────────────────────────────────
' HELPER: browser rename walk (v2.2.14)
' Sets each target-folder occurrence's Name to its filename without extension.
' Recurses only into sub-assemblies in the target folder; saves each such
' sub-assembly (not the top GA, which the caller saves) if it had renames.
' ─────────────────────────────────────────────────────────────────────────────
Sub BrowserRename_WalkOccs(oCompDef As ComponentDefinition, _
                           sTopPath As String, _
                           sTargetFolder As String, _
                           sLogPath As String, _
                           oVisited As System.Collections.Generic.HashSet(Of String), _
                           ByRef iRenamed As Integer)
    Dim sThisFull As String = ""
    Try
        sThisFull = oCompDef.Document.FullFileName
    Catch
        Return
    End Try
    If oVisited.Contains(sThisFull) Then Return
    oVisited.Add(sThisFull)

    Dim iRenamedHere As Integer = 0

    ' Snapshot occurrences
    Dim oOccList As New System.Collections.Generic.List(Of ComponentOccurrence)()
    Dim oOccSnap As ComponentOccurrence
    Try
        For Each oOccSnap In oCompDef.Occurrences
            oOccList.Add(oOccSnap)
        Next
    Catch
    End Try

    Dim oOcc As ComponentOccurrence
    Dim sOccPath As String
    Dim sBaseName As String
    Dim sOldOccName As String
    Dim sTryName As String
    Dim bNamed As Boolean
    Dim kSuffix As Integer
    Dim oChildDef As ComponentDefinition
    For Each oOcc In oOccList
        sOccPath = ""
        Try
            sOccPath = oOcc.Definition.Document.FullFileName
        Catch
        End Try
        If sOccPath = "" Then Continue For
        If Not IsSameOrUnderDirectory(sOccPath, sTargetFolder) Then Continue For

        ' Recurse into target-folder sub-assemblies first
        Try
            oChildDef = oOcc.Definition
            If oChildDef IsNot Nothing AndAlso oChildDef.Document.DocumentType = DocumentTypeEnum.kAssemblyDocumentObject Then
                BrowserRename_WalkOccs(oChildDef, sTopPath, sTargetFolder, sLogPath, oVisited, iRenamed)
            End If
        Catch
        End Try

        sBaseName = System.IO.Path.GetFileNameWithoutExtension(sOccPath)
        sOldOccName = ""
        Try
            sOldOccName = oOcc.Name
        Catch
        End Try
        If sOldOccName = sBaseName Then Continue For
        If sOldOccName.StartsWith(sBaseName & ":") Then Continue For

        bNamed = False
        sTryName = sBaseName
        Try
            oOcc.Name = sTryName
            bNamed = True
        Catch
        End Try
        If Not bNamed Then
            For kSuffix = 1 To 999
                sTryName = sBaseName & ":" & kSuffix
                Try
                    oOcc.Name = sTryName
                    bNamed = True
                Catch
                End Try
                If bNamed Then Exit For
            Next
        End If
        If bNamed Then
            iRenamed += 1
            iRenamedHere += 1
            Try : System.IO.File.AppendAllText(sLogPath, "BROWSER-RENAME: " & sOldOccName & " -> " & sTryName & vbCrLf) : Catch : End Try
        Else
            Try : System.IO.File.AppendAllText(sLogPath, "BROWSER-RENAME-FAIL: " & sOldOccName & vbCrLf) : Catch : End Try
        End If
    Next

    ' Save this sub-assembly if it had renames (the caller saves the top GA)
    If iRenamedHere > 0 AndAlso Not String.Equals(sThisFull, sTopPath, StringComparison.OrdinalIgnoreCase) Then
        Try
            Dim oFASub As System.IO.FileAttributes = System.IO.File.GetAttributes(sThisFull)
            If (oFASub And System.IO.FileAttributes.ReadOnly) = System.IO.FileAttributes.ReadOnly Then
                System.IO.File.SetAttributes(sThisFull, oFASub And Not System.IO.FileAttributes.ReadOnly)
            End If
            oCompDef.Document.Save2(False)
            Try : System.IO.File.AppendAllText(sLogPath, "BROWSER-RENAME-SAVED: " & System.IO.Path.GetFileName(sThisFull) & vbCrLf) : Catch : End Try
        Catch exSubSave As Exception
            Try : System.IO.File.AppendAllText(sLogPath, "BROWSER-RENAME-SAVE-FAIL: " & System.IO.Path.GetFileName(sThisFull) & " — " & exSubSave.Message & vbCrLf) : Catch : End Try
        End Try
    End If
End Sub


' ─────────────────────────────────────────────────────────────────────────────
' HELPER: apply string-replacement rules to a new full path's base name (v2.2.15)
' v2.2.17: case-insensitive replace on the file name without extension.
' If the rules would empty the name, the original is kept.
' ─────────────────────────────────────────────────────────────────────────────
Function ApplyStringRules(sNewFull As String, _
                          oRules As System.Collections.Generic.List(Of String())) As String
    If oRules Is Nothing Then Return sNewFull
    If oRules.Count = 0 Then Return sNewFull
    Dim sDir As String = System.IO.Path.GetDirectoryName(sNewFull)
    Dim sBase As String = System.IO.Path.GetFileNameWithoutExtension(sNewFull)
    Dim sExt As String = System.IO.Path.GetExtension(sNewFull)
    Dim sResult As String = sBase
    Dim aPair As String()
    For Each aPair In oRules
        If aPair(0) <> "" Then
            sResult = System.Text.RegularExpressions.Regex.Replace(sResult, _
                System.Text.RegularExpressions.Regex.Escape(aPair(0)), _
                aPair(1).Replace("$", "$$"), _
                System.Text.RegularExpressions.RegexOptions.IgnoreCase)
        End If
    Next
    If sResult.Trim() = "" Then Return sNewFull
    Return System.IO.Path.Combine(sDir, sResult & sExt)
End Function


' ─────────────────────────────────────────────────────────────────────────────
' HELPER: read CS_SourcePath from a file (v2.2.15)
' v2.2.17: checks oCache first.  On a miss it uses the in-session document if
' open, else opens invisibly, reads, and closes it; the result is cached.
' (The Inventor API has no iProperty read without opening the document.)
' ─────────────────────────────────────────────────────────────────────────────
Function ReadCSSourcePath(sPath As String, _
                          oCache As System.Collections.Generic.Dictionary(Of String, String)) As String
    If oCache IsNot Nothing AndAlso oCache.ContainsKey(sPath) Then Return oCache(sPath)
    Dim sVal As String = ""
    Dim oDoc As Document = Nothing
    Try
        oDoc = ThisApplication.Documents.ItemByName(sPath)
    Catch
    End Try
    If oDoc IsNot Nothing Then
        Try
            sVal = oDoc.PropertySets("Inventor User Defined Properties").Item("CS_SourcePath").Value
        Catch
        End Try
        If sVal Is Nothing Then sVal = ""
        If oCache IsNot Nothing Then oCache(sPath) = sVal
        Return sVal
    End If
    Dim bPrevSilent As Boolean = ThisApplication.SilentOperation
    ThisApplication.SilentOperation = True
    Try
        Dim oTmp As Document = ThisApplication.Documents.Open(sPath, False)
        Try
            sVal = oTmp.PropertySets("Inventor User Defined Properties").Item("CS_SourcePath").Value
        Catch
        End Try
        Try : oTmp.Close(True) : Catch : End Try
    Catch
    Finally
        ThisApplication.SilentOperation = bPrevSilent
    End Try
    If sVal Is Nothing Then sVal = ""
    If oCache IsNot Nothing Then oCache(sPath) = sVal
    Return sVal
End Function


' ─────────────────────────────────────────────────────────────────────────────
' HELPER: pick the target path for a source (v2.2.15)
'   - free name                                   -> use it
'   - exists, CS_SourcePath = source              -> REUSE (provenance match)
'   - exists, CS_SourcePath mismatch or blank     -> _N suffix (provenance mismatch)
'   - already mapped by another source this run   -> _N suffix (in-run collision)
' In the suffix loop an existing _N file whose CS_SourcePath matches is reused.
' bReused is set True when an existing file is reused.
' v2.2.17: no prefix-collision reuse; bRuleChanged is kept in the signature
' but no longer affects the decision.  Returns "" (SUFFIX-EXHAUSTED) when no
' free _N name is found below 10000; callers treat "" as skip.
' ─────────────────────────────────────────────────────────────────────────────
Function ResolveTarget(sSource As String, _
                       sCand As String, _
                       bRuleChanged As Boolean, _
                       oMappedTargets As System.Collections.Generic.HashSet(Of String), _
                       sLogPath As String, _
                       ByRef bReused As Boolean, _
                       oSourcePathCache As System.Collections.Generic.Dictionary(Of String, String)) As String
    bReused = False
    Dim sReason As String = ""
    Dim sExistingSrc As String = ""
    If Not oMappedTargets.Contains(sCand) Then
        If Not System.IO.File.Exists(sCand) Then Return sCand
        sExistingSrc = ReadCSSourcePath(sCand, oSourcePathCache)
        If sExistingSrc <> "" AndAlso String.Equals(sExistingSrc, sSource, StringComparison.OrdinalIgnoreCase) Then
            bReused = True
            Try : System.IO.File.AppendAllText(sLogPath, "REUSE: " & System.IO.Path.GetFileName(sCand) & " (provenance match)" & vbCrLf) : Catch : End Try
            Return sCand
        End If
        sReason = "provenance mismatch"
    Else
        sReason = "in-run collision"
    End If

    Dim sDir As String = System.IO.Path.GetDirectoryName(sCand)
    Dim sBase As String = System.IO.Path.GetFileNameWithoutExtension(sCand)
    Dim sExt As String = System.IO.Path.GetExtension(sCand)
    Dim sTry As String = sCand
    Dim iSfx As Integer = 2
    Do While iSfx < 10000
        sTry = System.IO.Path.Combine(sDir, sBase & "_" & iSfx & sExt)
        If Not oMappedTargets.Contains(sTry) Then
            If Not System.IO.File.Exists(sTry) Then
                Try : System.IO.File.AppendAllText(sLogPath, "SUFFIX: " & System.IO.Path.GetFileName(sTry) & " (" & sReason & ")" & vbCrLf) : Catch : End Try
                Return sTry
            End If
            sExistingSrc = ReadCSSourcePath(sTry, oSourcePathCache)
            If sExistingSrc <> "" AndAlso String.Equals(sExistingSrc, sSource, StringComparison.OrdinalIgnoreCase) Then
                bReused = True
                Try : System.IO.File.AppendAllText(sLogPath, "REUSE: " & System.IO.Path.GetFileName(sTry) & " (provenance match)" & vbCrLf) : Catch : End Try
                Return sTry
            End If
        End If
        iSfx += 1
    Loop
    ' v2.2.17: no free name found — do not return a name that may already exist
    Try : System.IO.File.AppendAllText(sLogPath, "SUFFIX-EXHAUSTED: " & sBase & vbCrLf) : Catch : End Try
    Return ""
End Function

' ═══════════════════════════════════════════════════════════════════════════════
' ProcessOrphanSubTree  (v2.2.27)
' Performs a full WalkTree + Phase-2 SaveAs + Phase-3 ref-fix on an orphan
' assembly that is referenced by a drawing but absent from the main GA tree.
' Mirrors what the main rule does for the GA:
'   Phase 1 lite : WalkTree discovers all descendants → oOrphMap
'   Phase 2 lite : SaveAs each sub-file deepest-first, write 3 CS_ properties
'   Phase 3 lite : open each new .iam copy, replace stale old refs via oActualMap
' All old→new mappings are added to oActualMap so the calling drawing-relink
' pass can point the drawing at the correct new top-level assembly.
'
' Parameters
'   oOrphTopDoc      — already-open Document handle for the orphan top assembly
'   sOrphOrigPath    — path as stored in the drawing (used as oActualMap key)
'   sOrphResolvedPath— path actually on disk (may differ if Vault resolved it)
'   sOldProjectRoot  — old project root folder (from main GA run)
'   sNewPrefix       — new project prefix   (from main GA run)
'   sTargetFolder    — target copy folder   (from main GA run)
'   oActualMap       — shared old→new map; entries added here by this Sub
'   oStringRules     — find/replace string rules (pass main oStringRules)
'   oNameOverrides   — per-model name overrides (pass empty dict for orphans)
'   sLogPath         — log file path
' ═══════════════════════════════════════════════════════════════════════════════
Sub ProcessOrphanSubTree(oOrphTopDoc As Document, _
                          sOrphOrigPath As String, _
                          sOrphResolvedPath As String, _
                          sOldProjectRoot As String, _
                          sNewPrefix As String, _
                          sTargetFolder As String, _
                          oActualMap As System.Collections.Generic.Dictionary(Of String, String), _
                          oStringRules As System.Collections.Generic.List(Of String()), _
                          oNameOverrides As System.Collections.Generic.Dictionary(Of String, String), _
                          sLogPath As String)

    ' ── Phase 1 lite: WalkTree ───────────────────────────────────────────────
    Dim oOrphMap     As New System.Collections.Generic.Dictionary(Of String, String)(StringComparer.OrdinalIgnoreCase)
    Dim oOrphSeen    As New System.Collections.Generic.HashSet(Of String)(StringComparer.OrdinalIgnoreCase)
    Dim oOrphMapped  As New System.Collections.Generic.HashSet(Of String)(StringComparer.OrdinalIgnoreCase)
    Dim oOrphOpened  As New System.Collections.Generic.List(Of Document)()
    Dim oOrphCache   As New System.Collections.Generic.Dictionary(Of String, String)(StringComparer.OrdinalIgnoreCase)
    Dim oOrphReuse   As New System.Collections.Generic.HashSet(Of String)(StringComparer.OrdinalIgnoreCase)

    Try
        WalkTree(oOrphTopDoc, sOldProjectRoot, sNewPrefix, sTargetFolder, _
                 oOrphMap, oOrphSeen, sLogPath, oOrphMapped, oOrphOpened, _
                 oStringRules, oOrphReuse, oOrphCache, oNameOverrides)
    Catch exOrphWalk As Exception
        Try : System.IO.File.AppendAllText(sLogPath, _
            "ORPHAN-WALK-FAIL: " & System.IO.Path.GetFileName(sOrphOrigPath) & _
            " — " & exOrphWalk.Message & vbCrLf) : Catch : End Try
        Return
    End Try

    ' Ensure the top-level assembly itself is in the map (WalkTree includes the
    ' root if it falls under sOldProjectRoot; guard in case it doesn't).
    If Not oOrphMap.ContainsKey(sOrphResolvedPath) Then
        Dim sOrphTopNew As String = ComputeNewName(sOrphResolvedPath, sOldProjectRoot, sNewPrefix, sTargetFolder)
        If sOrphTopNew <> "" Then oOrphMap(sOrphResolvedPath) = sOrphTopNew
    End If
    ' If the drawing stored a different path (Vault-resolved), map that too.
    If sOrphOrigPath <> sOrphResolvedPath AndAlso oOrphMap.ContainsKey(sOrphResolvedPath) Then
        oOrphMap(sOrphOrigPath) = oOrphMap(sOrphResolvedPath)
    End If

    Try : System.IO.File.AppendAllText(sLogPath, _
        "ORPHAN-WALK: " & System.IO.Path.GetFileName(sOrphOrigPath) & _
        " — " & oOrphMap.Count & " file(s) in sub-tree" & vbCrLf) : Catch : End Try

    ' NOTE: oOrphOpened docs are kept open here — Phase 2 lite finds them via
    ' ItemByName so it doesn't need to re-open them. Close them AFTER Phase 3.

    ' ── Phase 2 lite: copy deepest-first; provenance on destination ONLY ──
    Dim oOrphKeys As New System.Collections.Generic.List(Of String)(oOrphMap.Keys)
    oOrphKeys.Sort(Function(a2, b2) SweeperPathDepth(b2).CompareTo(SweeperPathDepth(a2)))

    Dim sOrphOld2 As String
    Dim sOrphNew2 As String
    Dim oOrphDoc2 As Document
    Dim bOrphO2 As Boolean
    Dim oOrphCopied As New System.Collections.Generic.HashSet(Of String)(StringComparer.OrdinalIgnoreCase)
    Dim oOrphNeedsProv As New System.Collections.Generic.Dictionary(Of String, String)(StringComparer.OrdinalIgnoreCase)

    For Each sOrphOld2 In oOrphKeys
        sOrphNew2 = oOrphMap(sOrphOld2)
        If sOrphNew2 = "" Then Continue For
        If System.IO.File.Exists(sOrphNew2) Then
            oActualMap(sOrphOld2) = sOrphNew2
            Try : System.IO.File.AppendAllText(sLogPath, _
                "ORPHAN-SUB-REUSE: " & System.IO.Path.GetFileName(sOrphOld2) & _
                " -> " & System.IO.Path.GetFileName(sOrphNew2) & vbCrLf) : Catch : End Try
            Continue For
        End If

        oOrphDoc2 = Nothing : bOrphO2 = False
        Dim bOrphCopied2 As Boolean = False
        Dim bOrphRaw2 As Boolean = False
        Try
            Try : oOrphDoc2 = ThisApplication.Documents.ItemByName(sOrphOld2) : Catch : End Try
            If oOrphDoc2 Is Nothing Then
                oOrphDoc2 = ThisApplication.Documents.Open(sOrphOld2, False)
                bOrphO2 = True
            End If
            Try
                oOrphDoc2.SaveAs(sOrphNew2, True)
                bOrphCopied2 = System.IO.File.Exists(sOrphNew2)
                If Not bOrphCopied2 Then
                    Try : System.IO.File.AppendAllText(sLogPath, _
                        "ORPHAN-SAVEAS-SILENT-FAIL: " & System.IO.Path.GetFileName(sOrphOld2) & vbCrLf) : Catch : End Try
                End If
            Catch exOrphSA2 As Exception
                Try : System.IO.File.AppendAllText(sLogPath, _
                    "ORPHAN-SAVEAS-FAIL: " & System.IO.Path.GetFileName(sOrphOld2) & _
                    " HRESULT=0x" & exOrphSA2.HResult.ToString("X8") & _
                    " — " & exOrphSA2.Message & vbCrLf) : Catch : End Try
                If Not System.IO.File.Exists(sOrphNew2) Then
                    Try
                        System.IO.File.Copy(sOrphOld2, sOrphNew2, False)
                        bOrphCopied2 = System.IO.File.Exists(sOrphNew2)
                        bOrphRaw2 = bOrphCopied2
                        If bOrphRaw2 Then
                            Try : System.IO.File.AppendAllText(sLogPath, _
                                "ORPHAN-FALLBACK-COPY: " & System.IO.Path.GetFileName(sOrphOld2) & _
                                " -> " & System.IO.Path.GetFileName(sOrphNew2) & vbCrLf) : Catch : End Try
                        End If
                    Catch exOrphFC2 As Exception
                        Try : System.IO.File.AppendAllText(sLogPath, _
                            "ORPHAN-FILECOPY-FAIL: " & System.IO.Path.GetFileName(sOrphOld2) & _
                            " — " & exOrphFC2.Message & vbCrLf) : Catch : End Try
                    End Try
                Else
                    Try : System.IO.File.AppendAllText(sLogPath, _
                        "ORPHAN-SAVEAS-PARTIAL: " & System.IO.Path.GetFileName(sOrphNew2) & _
                        " exists after exception; not accepted automatically" & vbCrLf) : Catch : End Try
                End If
            End Try

            ' Inventor may return normally but create no destination file.
            If Not bOrphCopied2 AndAlso Not System.IO.File.Exists(sOrphNew2) Then
                Try
                    System.IO.File.Copy(sOrphOld2, sOrphNew2, False)
                    bOrphCopied2 = System.IO.File.Exists(sOrphNew2)
                    bOrphRaw2 = bOrphCopied2
                    If bOrphCopied2 Then
                        Try : System.IO.File.AppendAllText(sLogPath, _
                            "ORPHAN-SILENT-FALLBACK-COPY: " & System.IO.Path.GetFileName(sOrphOld2) & _
                            " -> " & System.IO.Path.GetFileName(sOrphNew2) & vbCrLf) : Catch : End Try
                    End If
                Catch exOrphSilent2 As Exception
                    Try : System.IO.File.AppendAllText(sLogPath, _
                        "ORPHAN-SILENT-FALLBACK-FAIL: " & System.IO.Path.GetFileName(sOrphOld2) & _
                        " HRESULT=0x" & exOrphSilent2.HResult.ToString("X8") & _
                        " — " & exOrphSilent2.Message & vbCrLf) : Catch : End Try
                End Try
            End If

            If bOrphCopied2 Then
                oOrphCopied.Add(sOrphNew2)
                oActualMap(sOrphOld2) = sOrphNew2
                oOrphNeedsProv(sOrphNew2) = sOrphOld2
                Try : System.IO.File.AppendAllText(sLogPath, _
                    "ORPHAN-SUB-COPY: " & System.IO.Path.GetFileName(sOrphOld2) & _
                    " -> " & System.IO.Path.GetFileName(sOrphNew2) & _
                    If(bOrphRaw2, " [raw copy; ref repair pending]", " [SaveAs; ref repair pending]") & vbCrLf) : Catch : End Try
            Else
                Try : System.IO.File.AppendAllText(sLogPath, _
                    "ORPHAN-SUB-FAIL: " & System.IO.Path.GetFileName(sOrphOld2) & _
                    " — destination not created" & vbCrLf) : Catch : End Try
            End If
        Catch exOrphSub As Exception
            Try : System.IO.File.AppendAllText(sLogPath, _
                "ORPHAN-SUB-FAIL: " & System.IO.Path.GetFileName(sOrphOld2) & _
                " — " & exOrphSub.Message & vbCrLf) : Catch : End Try
        Finally
            If bOrphO2 AndAlso oOrphDoc2 IsNot Nothing Then
                Try : oOrphDoc2.Close(True) : Catch : End Try
            End If
        End Try
    Next

    ' ── Phase 3 lite: fix refs inside each new .iam copy ─────────────────────
    ' Each new assembly still points at the OLD sub-part paths post-SaveAs.
    ' Walk shallowest-first (shortest path) so parent assemblies are fixed after
    ' their children are already saved and correct on disk.
    oOrphKeys.Sort(Function(a2, b2) SweeperPathDepth(b2).CompareTo(SweeperPathDepth(a2)))
    For Each sOrphOld2 In oOrphKeys
        sOrphNew2 = oOrphMap(sOrphOld2)
        If sOrphNew2 = "" OrElse Not System.IO.File.Exists(sOrphNew2) Then Continue For
        If System.IO.Path.GetExtension(sOrphNew2).ToUpper() <> ".IAM" Then Continue For
        If Not oOrphCopied.Contains(sOrphNew2) Then Continue For
        oOrphDoc2 = Nothing : bOrphO2 = False
        Try
            Try : oOrphDoc2 = ThisApplication.Documents.ItemByName(sOrphNew2) : Catch : End Try
            If oOrphDoc2 Is Nothing Then
                oOrphDoc2 = ThisApplication.Documents.Open(sOrphNew2, True)
                bOrphO2 = True
            End If
            Dim iOrphFixed As Integer = 0
            For Each oOrphFDObj As Object In oOrphDoc2.ReferencedFileDescriptors
                Dim oOrphFD As FileDescriptor = TryCast(oOrphFDObj, FileDescriptor)
                If oOrphFD Is Nothing Then Continue For
                Dim sOrphFDPath As String = ""
                Try : sOrphFDPath = oOrphFD.FullFileName : Catch : Continue For : End Try
                If Not oActualMap.ContainsKey(sOrphFDPath) Then Continue For
                Dim sOrphFDNew As String = oActualMap(sOrphFDPath)
                If Not System.IO.File.Exists(sOrphFDNew) Then Continue For
                Try
                    oOrphFD.ReplaceReference(sOrphFDNew)
                    iOrphFixed += 1
                Catch exOrphFD As Exception
                    Try : System.IO.File.AppendAllText(sLogPath, _
                        "ORPHAN-SUB-FD-FAIL: " & System.IO.Path.GetFileName(sOrphNew2) & _
                        " ref " & System.IO.Path.GetFileName(sOrphFDPath) & _
                        " — " & exOrphFD.Message & vbCrLf) : Catch : End Try
                End Try
            Next
            If oOrphNeedsProv.ContainsKey(sOrphNew2) Then
                Try
                    SetSweeperCopyProperty(oOrphDoc2, "CS_SourcePath", oOrphNeedsProv(sOrphNew2))
                    SetSweeperCopyProperty(oOrphDoc2, "CS_CopyProject", sNewPrefix)
                    SetSweeperCopyProperty(oOrphDoc2, "CS_CopyDate", Now.ToString("yyyy-MM-dd"))
                    Try : System.IO.File.AppendAllText(sLogPath, _
                        "ORPHAN-PROV-SET: " & System.IO.Path.GetFileName(sOrphNew2) & vbCrLf) : Catch : End Try
                Catch exOrphProv As Exception
                    Try : System.IO.File.AppendAllText(sLogPath, _
                        "ORPHAN-PROV-FAIL: " & System.IO.Path.GetFileName(sOrphNew2) & _
                        " — " & exOrphProv.Message & vbCrLf) : Catch : End Try
                End Try
            End If
            If iOrphFixed > 0 OrElse oOrphNeedsProv.ContainsKey(sOrphNew2) Then
                oOrphDoc2.Save2(False)
                Try : System.IO.File.AppendAllText(sLogPath, _
                    "ORPHAN-SUB-REFFIX: " & System.IO.Path.GetFileName(sOrphNew2) & _
                    " — " & iOrphFixed & " ref(s) fixed" & vbCrLf) : Catch : End Try
            End If
        Catch exOrphRef As Exception
            Try : System.IO.File.AppendAllText(sLogPath, _
                "ORPHAN-SUB-REFFIX-FAIL: " & System.IO.Path.GetFileName(sOrphNew2) & _
                " — " & exOrphRef.Message & vbCrLf) : Catch : End Try
        End Try
        If bOrphO2 AndAlso oOrphDoc2 IsNot Nothing Then
            Try : oOrphDoc2.Close(True) : Catch : End Try
        End If
    Next

    ' Write provenance to newly copied orphan parts (no child references).
    For Each sOrphProvNew As String In oOrphNeedsProv.Keys
        If System.IO.Path.GetExtension(sOrphProvNew).ToUpper() <> ".IPT" Then Continue For
        Dim oOrphPartProv As Document = Nothing
        Try
            oOrphPartProv = ThisApplication.Documents.Open(sOrphProvNew, False)
            SetSweeperCopyProperty(oOrphPartProv, "CS_SourcePath", oOrphNeedsProv(sOrphProvNew))
            SetSweeperCopyProperty(oOrphPartProv, "CS_CopyProject", sNewPrefix)
            SetSweeperCopyProperty(oOrphPartProv, "CS_CopyDate", Now.ToString("yyyy-MM-dd"))
            oOrphPartProv.Save2(False)
            Try : System.IO.File.AppendAllText(sLogPath, _
                "ORPHAN-PROV-SAVED: " & System.IO.Path.GetFileName(sOrphProvNew) & vbCrLf) : Catch : End Try
        Catch exOrphPartProv As Exception
            Try : System.IO.File.AppendAllText(sLogPath, _
                "ORPHAN-PROV-FAIL: " & System.IO.Path.GetFileName(sOrphProvNew) & _
                " — " & exOrphPartProv.Message & vbCrLf) : Catch : End Try
        Finally
            If oOrphPartProv IsNot Nothing Then
                Try : oOrphPartProv.Close(True) : Catch : End Try
            End If
        End Try
    Next

    ' Close all documents that WalkTree opened (now safe — Phase 2 & 3 are done)
    For Each oWD As Document In oOrphOpened
        Try : oWD.Close(True) : Catch : End Try
    Next
    oOrphOpened.Clear()

End Sub

' ─────────────────────────────────────────────────────────────────────────────
' v2.2.31 helpers — source-safe provenance and directory depth
' ─────────────────────────────────────────────────────────────────────────────
Function SweeperPathDepth(sPath As String) As Integer
    If String.IsNullOrEmpty(sPath) Then Return 0
    Return sPath.Replace("/"c, "\"c).Split("\"c).Length
End Function

Sub SetSweeperCopyProperty(oCopyDoc As Document, sPropName As String, sPropValue As String)
    Dim oProps As PropertySet = oCopyDoc.PropertySets.Item("Inventor User Defined Properties")
    Try
        oProps.Item(sPropName).Value = sPropValue
    Catch
        oProps.Add(sPropValue, sPropName)
    End Try
End Sub


' ============================================================================
' BBn urgent TEST: target-only project metadata refresh (no FG changes).
' Must be executed against disposable, checked-out copies after reviewing log.
' ============================================================================
Sub RunCopiedProjectMetadataPass(sTargetFolder As String, sOldPrefix As String, _
    sNewPrefix As String, oActualMap As System.Collections.Generic.Dictionary(Of String, String), _
    oDwgList As System.Collections.Generic.List(Of String), sDwgEntryPath As String, _
    bFromDwg As Boolean, sLogPath As String, _
    ByRef iModelChanged As Integer, ByRef iDrawingChanged As Integer, ByRef iFailures As Integer)

    Dim oTargets As New System.Collections.Generic.HashSet(Of String)(StringComparer.OrdinalIgnoreCase)
    For Each sTarget As String In oActualMap.Values
        If IsSameOrUnderDirectory(sTarget, sTargetFolder) Then oTargets.Add(sTarget)
    Next
    ' Include previously copied targets on zero-copy reruns; never recurse into source.
    For Each sExt As String In New String() {"*.iam", "*.ipt"}
        For Each sTarget As String In System.IO.Directory.GetFiles(sTargetFolder, sExt, System.IO.SearchOption.TopDirectoryOnly)
            oTargets.Add(sTarget)
        Next
    Next
    Try : System.IO.File.AppendAllText(sLogPath, vbCrLf & "=== BBn METADATA TEST PASS ===" & vbCrLf) : Catch : End Try
    If String.IsNullOrWhiteSpace(sOldPrefix) OrElse String.IsNullOrWhiteSpace(sNewPrefix) _
       OrElse String.Equals(sOldPrefix, sNewPrefix, StringComparison.OrdinalIgnoreCase) Then
        Try : System.IO.File.AppendAllText(sLogPath, "META-SKIP: invalid or unchanged project prefixes" & vbCrLf) : Catch : End Try
        Return
    End If
    Dim bPriorSilent As Boolean = ThisApplication.SilentOperation
    ThisApplication.SilentOperation = True
    Try
        For Each sTarget As String In oTargets
            If Not IsSameOrUnderDirectory(sTarget, sTargetFolder) OrElse Not System.IO.File.Exists(sTarget) Then Continue For
            If IsTopLevelContentCenter(sTarget) OrElse _
               System.Text.RegularExpressions.Regex.IsMatch(System.IO.Path.GetFileNameWithoutExtension(sTarget), _
                   "^(PJ[0-9]+-)?JC[0-9]+$", System.Text.RegularExpressions.RegexOptions.IgnoreCase) Then
                Try : System.IO.File.AppendAllText(sLogPath, "META-JC-CC-SKIP: " & sTarget & vbCrLf) : Catch : End Try
                Continue For
            End If
            If (System.IO.File.GetAttributes(sTarget) And System.IO.FileAttributes.ReadOnly) <> 0 Then
                Try : System.IO.File.AppendAllText(sLogPath, "META-READONLY-SKIP: " & sTarget & vbCrLf) : Catch : End Try
                Continue For
            End If
            Dim oDoc As Document = Nothing
            Dim bOpened As Boolean = False
            Try
                Try : oDoc = ThisApplication.Documents.ItemByName(sTarget) : Catch : End Try
                If oDoc Is Nothing Then
                    oDoc = ThisApplication.Documents.Open(sTarget, False)
                    bOpened = True
                End If
                Dim bChanged As Boolean = False
                Dim oDesign As PropertySet = oDoc.PropertySets.Item("Design Tracking Properties")
                Dim oCustom As PropertySet = oDoc.PropertySets.Item("Inventor User Defined Properties")
                bChanged = ReplaceExistingPrefix(oDesign, "Part Number", sOldPrefix, sNewPrefix) Or bChanged
                ' Match any leading PJ project code in project-owned model SPECIFICATION.
                bChanged = ReplaceLeadingProjectCode(oCustom, "SPECIFICATION", sNewPrefix, sLogPath, sTarget) Or bChanged
                bChanged = SetExistingNonblankProperty(oCustom, "PROJECT NUMBER", sNewPrefix, sLogPath, sTarget) Or bChanged
                bChanged = PadFiveDigitProperty(oCustom, "DRAWING REF", sLogPath, sTarget) Or bChanged
                bChanged = PadFiveDigitProperty(oCustom, "ITEM NUMBER", sLogPath, sTarget) Or bChanged
                If bChanged Then
                    oDoc.Save2(False)
                    iModelChanged += 1
                    Try : System.IO.File.AppendAllText(sLogPath, "META-MODEL-SAVED: " & sTarget & vbCrLf) : Catch : End Try
                End If
            Catch ex As Exception
                iFailures += 1
                Try : System.IO.File.AppendAllText(sLogPath, "META-MODEL-FAIL: " & sTarget & " — " & ex.Message & vbCrLf) : Catch : End Try
            Finally
                If bOpened AndAlso oDoc IsNot Nothing Then
                    Try
                        If Not oDoc.Dirty Then oDoc.Close(True)
                    Catch
                    End Try
                End If
            End Try
        Next

        If bFromDwg Then
            Dim oDrawings As New System.Collections.Generic.HashSet(Of String)(StringComparer.OrdinalIgnoreCase)
            ' Metadata applies to TARGET drawing copies only, never the original list.
            For Each sPattern As String In New String() {"*.idw", "*.dwg"}
                For Each sCandidate As String In System.IO.Directory.GetFiles(sTargetFolder, sPattern, System.IO.SearchOption.AllDirectories)
                    oDrawings.Add(sCandidate)
                Next
            Next
            Try : System.IO.File.AppendAllText(sLogPath, "META-DWG-TARGET-COUNT: " & oDrawings.Count & vbCrLf) : Catch : End Try
            For Each sDrawing As String In oDrawings
                ' Only drawings in target folder: never change original drawing.
                If Not IsSameOrUnderDirectory(sDrawing, sTargetFolder) Then
                    Try : System.IO.File.AppendAllText(sLogPath, "META-DWG-OUTSIDE-TARGET-SKIP: " & sDrawing & vbCrLf) : Catch : End Try
                    Continue For
                End If
                If Not System.IO.File.Exists(sDrawing) Then Continue For
                If (System.IO.File.GetAttributes(sDrawing) And System.IO.FileAttributes.ReadOnly) <> 0 Then
                    Try : System.IO.File.AppendAllText(sLogPath, "META-DWG-READONLY-SKIP: " & sDrawing & vbCrLf) : Catch : End Try
                    Continue For
                End If
                Dim oDwg As Document = Nothing
                Dim bOpenedDwg As Boolean = False
                Try
                    Try : oDwg = ThisApplication.Documents.ItemByName(sDrawing) : Catch : End Try
                    If oDwg Is Nothing Then
                        oDwg = ThisApplication.Documents.Open(sDrawing, False)
                        bOpenedDwg = True
                    End If
                    Dim oCust As PropertySet = oDwg.PropertySets.Item("Inventor User Defined Properties")
                    Dim oProject As PropertySet = oDwg.PropertySets.Item("Design Tracking Properties")
                    Dim bChanged As Boolean = False
                    ' Prefix replacement in every existing text custom property.
                    For Each oProp As Inventor.Property In oCust
                        Try
                            If TypeOf oProp.Value Is String Then
                                Dim sBefore As String = CStr(oProp.Value)
                                Dim sAfter As String = ReplacePrefixToken(sBefore, sOldPrefix, sNewPrefix)
                                If sBefore <> sAfter Then
                                    oProp.Value = sAfter
                                    bChanged = True
                                End If
                            End If
                        Catch exProp As Exception
                            Try : System.IO.File.AppendAllText(sLogPath, "META-DWG-PROP-FAIL: " & sDrawing & " — " & exProp.Message & vbCrLf) : Catch : End Try
                        End Try
                    Next
                    ' Revision Number is in Inventor Summary Information.
                    bChanged = SetPropertyValue(oProject, "Revision Number", "A") Or bChanged
                    ' The drawing number is normally derived from the new drawing filename.
                    ' Do not clear it during reset; preserve/replace its actual value below.
                    Dim aFields As String() = New String() {
                        "APPROVED","APPROVED DATE","CHECKED","CHECKED DATE",
                        "DOM APPROVED","DOM APPROVED DATE","DRAWN","DRAWN DATE",
                        "MECHANICAL ENGINEER APPROVED","MECHANICAL ENGINEER DATE",
                        "PROCESS ENG APPROVED","PROCESS ENG DATE","PROJ MANAGER APPROVED",
                        "PROJ MANAGER DATE","STRUCTURAL ENG APPROVED","STRUCTURAL ENG DATE",
                        "3SYSTEM","4EQUIPMENT","5DRAWING TYPE","DRAWING_DESCRIPTION_1",
                        "DRAWING_DESCRIPTION_2","DRAWING_DESCRIPTION_3",
                        "SAVE DATE","SAVED TIME","SAVED BY","1st REV","1st REV BY",
                        "1st REV DATE","1st REV DESCRIPTION","1st REV CHECKED",
                        "1st REV ENGINEER","1st REV APPROVED",
                        "REVISION","EQUIPMENT","Client_DRG_No","CLIENT_TB_LINE1",
                        "CLIENT_TB_LINE2","CLIENT_TB_LINE3","DOM DATE",
                        "CLIENT DOCUMENT No.","1CLIENT_LINGUAL","2PLANT/PROJECT_LINGUAL",
                        "4EQUIPMENT_LINGUAL","5DRAWING TYPE_LINGUAL","3SYSTEM_LINGUAL",
                        "SPECIFICATION"}
                    Dim sToday As String = Now.ToString("dd/MM/yyyy")
                    For Each sField As String In aFields
                        Dim sValue As String = ""
                        Select Case sField
                            Case "DRAWN", "1st REV BY" : sValue = "XX"
                            Case "DRAWN DATE", "SAVE DATE", "1st REV DATE", "DOM DATE" : sValue = sToday
                            Case "SAVED TIME" : sValue = Now.ToString("HH:mm:ss")
                            Case "SAVED BY" : sValue = "Whughes"
                            Case "3SYSTEM" : sValue = "ROUGHER CELL 1"
                            Case "4EQUIPMENT" : sValue = "EQUIPMENT No. TBC"
                            Case "1st REV", "REVISION" : sValue = "A"
                            Case "1st REV DESCRIPTION" : sValue = "PRELIMINARY ISSUE"
                        End Select
                        bChanged = SetPropertyValue(oCust, sField, sValue) Or bChanged
                    Next
                    ' Explicitly set drawing-number custom property from the target drawing name.
                    bChanged = SetPropertyValue(oCust, "DRAWING_NUMBER", _
                        System.IO.Path.GetFileNameWithoutExtension(sDrawing)) Or bChanged
                    For iRev As Integer = 2 To 7
                        For Each sSuffix As String In New String() {"", " BY", " DATE", " DESCRIPTION", " CHECKED", " ENGINEER", " APPROVED"}
                            Dim sOrdinal As String = iRev.ToString() & If(iRev = 2, "nd", If(iRev = 3, "rd", "th"))
                            bChanged = SetPropertyValue(oCust, sOrdinal & " REV" & sSuffix, "") Or bChanged
                        Next
                    Next
                    If bChanged Then
                        oDwg.Save2(False)
                        iDrawingChanged += 1
                        Try : System.IO.File.AppendAllText(sLogPath, "META-DWG-SAVED: " & sDrawing & vbCrLf) : Catch : End Try
                    End If
                Catch ex As Exception
                    iFailures += 1
                    Try : System.IO.File.AppendAllText(sLogPath, "META-DWG-FAIL: " & sDrawing & " — " & ex.Message & vbCrLf) : Catch : End Try
                Finally
                    If bOpenedDwg AndAlso oDwg IsNot Nothing Then
                        Try
                            If Not oDwg.Dirty Then oDwg.Close(True)
                        Catch
                        End Try
                    End If
                End Try
            Next
        End If
    Finally
        ThisApplication.SilentOperation = bPriorSilent
    End Try
    Try : System.IO.File.AppendAllText(sLogPath, "META-SUMMARY: models=" & iModelChanged & _
        " drawings=" & iDrawingChanged & " failures=" & iFailures & vbCrLf) : Catch : End Try
End Sub

Function ReplacePrefixToken(sValue As String, sOld As String, sNew As String) As String
    If String.IsNullOrEmpty(sValue) OrElse String.IsNullOrEmpty(sOld) Then Return sValue
    Dim sPattern As String = "(?<![A-Za-z0-9])" & _
        System.Text.RegularExpressions.Regex.Escape(sOld) & "(?![A-Za-z0-9])"
    Return System.Text.RegularExpressions.Regex.Replace(sValue, sPattern, sNew, _
        System.Text.RegularExpressions.RegexOptions.IgnoreCase)
End Function

Function ReplaceExistingPrefix(oSet As PropertySet, sName As String, sOld As String, sNew As String) As Boolean
    Try
        Dim oP As Inventor.Property = oSet.Item(sName)
        If Not TypeOf oP.Value Is String Then Return False
        Dim sBefore As String = CStr(oP.Value)
        Dim sAfter As String = ReplacePrefixToken(sBefore, sOld, sNew)
        If sBefore = sAfter Then Return False
        oP.Value = sAfter
        Return True
    Catch
        Return False
    End Try
End Function

Function SetPropertyValue(oSet As PropertySet, sName As String, sValue As String) As Boolean
    Try
        Dim oP As Inventor.Property = oSet.Item(sName)
        If String.Equals(Convert.ToString(oP.Value), sValue, StringComparison.Ordinal) Then Return False
        oP.Value = sValue
        Return True
    Catch
        oSet.Add(sValue, sName)
        Return True
    End Try
End Function


' TEST2 conservative model-property helpers; changes are logged before save.
Function ReplaceLeadingProjectCode(oSet As PropertySet, sName As String, _
    sNew As String, sLog As String, sFile As String) As Boolean
    Try
        Dim oP As Inventor.Property = oSet.Item(sName)
        If Not TypeOf oP.Value Is String Then Return False
        Dim sOldValue As String = CStr(oP.Value)
        Dim sNewValue As String = System.Text.RegularExpressions.Regex.Replace(sOldValue, _
            "^PJ[0-9]{5}(?=-)", sNew, System.Text.RegularExpressions.RegexOptions.IgnoreCase)
        If String.Equals(sOldValue, sNewValue, StringComparison.Ordinal) Then Return False
        oP.Value = sNewValue
        Try : System.IO.File.AppendAllText(sLog, "META-SPEC: " & sFile & " " & sOldValue & " -> " & sNewValue & vbCrLf) : Catch : End Try
        Return True
    Catch
        Return False
    End Try
End Function

Function SetExistingNonblankProperty(oSet As PropertySet, sName As String, _
    sNew As String, sLog As String, sFile As String) As Boolean
    Try
        Dim oP As Inventor.Property = oSet.Item(sName)
        Dim sOld As String = Convert.ToString(oP.Value)
        If String.IsNullOrWhiteSpace(sOld) OrElse String.Equals(sOld, sNew, StringComparison.Ordinal) Then Return False
        oP.Value = sNew
        Try : System.IO.File.AppendAllText(sLog, "META-PROJECT: " & sFile & " " & sOld & " -> " & sNew & vbCrLf) : Catch : End Try
        Return True
    Catch
        Return False
    End Try
End Function

Function PadFiveDigitProperty(oSet As PropertySet, sName As String, _
    sLog As String, sFile As String) As Boolean
    Try
        Dim oP As Inventor.Property = oSet.Item(sName)
        Dim sOld As String = Convert.ToString(oP.Value)
        If Not System.Text.RegularExpressions.Regex.IsMatch(sOld, "^[0-9]{5}$") Then Return False
        oP.Value = "0" & sOld
        Try : System.IO.File.AppendAllText(sLog, "META-PAD: " & sFile & " " & sName & " " & sOld & " -> 0" & sOld & vbCrLf) : Catch : End Try
        Return True
    Catch
        Return False
    End Try
End Function
