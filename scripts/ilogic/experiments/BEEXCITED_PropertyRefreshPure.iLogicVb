' BEEXCITED Property Refresh 01 — pure planning primitives, v0.1.0-preview
' Experimental library component. No Inventor calls, no file writes, no UI.
' Not an APPLY engine. Inventor compilation and integration are NOT validated.
Imports System
Imports System.Collections.Generic
Imports System.Text.RegularExpressions

Public Module BEEXCITED_PropertyRefreshPure
    Public Const EngineVersion As String = "0.1.0-preview"

    Public Class PropertyChange
        Public Property FilePath As String
        Public Property PropertySetName As String
        Public Property PropertyName As String
        Public Property OldValue As String
        Public Property NewValue As String
        Public Property Reason As String
    End Class

    Public Function NormalizeProjectPrefix(ByVal proposed As String) As String
        If proposed Is Nothing Then Throw New ArgumentException("Project prefix is required.")
        Dim result As String = proposed.Trim().ToUpperInvariant()
        If Not Regex.IsMatch(result, "^PJ[0-9]{5}$", RegexOptions.CultureInvariant) Then
            Throw New ArgumentException("Expected exactly PJ followed by five digits.")
        End If
        Return result
    End Function

    ' Replace ONLY the initial PJ#####- token; preserve the complete suffix.
    ' An absent or malformed prefix is never fabricated or repaired.
    Public Function ReplaceLeadingProjectPrefix(ByVal original As String, ByVal proposed As String) As String
        Dim prefix As String = NormalizeProjectPrefix(proposed)
        If original Is Nothing Then Return Nothing
        If Not Regex.IsMatch(original, "^PJ[0-9]{5}-", RegexOptions.IgnoreCase Or RegexOptions.CultureInvariant) Then
            Return original
        End If
        Return prefix & original.Substring(7)
    End Function

    ' Drawing identity must agree between existing property and filename.
    ' Preserve the existing property suffix; never derive it from filename.
    Public Function PlanDrawingNumber(ByVal existingValue As String, ByVal fileBaseName As String, ByVal proposed As String) As String
        Dim prefix As String = NormalizeProjectPrefix(proposed)
        If String.IsNullOrEmpty(existingValue) OrElse String.IsNullOrEmpty(fileBaseName) Then Return existingValue
        Dim expression As String = "^PJ[0-9]{5}-"
        If Not Regex.IsMatch(existingValue, expression, RegexOptions.IgnoreCase Or RegexOptions.CultureInvariant) Then Return existingValue
        If Not Regex.IsMatch(fileBaseName, expression, RegexOptions.IgnoreCase Or RegexOptions.CultureInvariant) Then Return existingValue
        If Not String.Equals(existingValue.Substring(0, 7), fileBaseName.Substring(0, 7), StringComparison.OrdinalIgnoreCase) Then Return existingValue
        Return prefix & existingValue.Substring(7)
    End Function

    ' No source-file or Vault mutations occur in this module.
    Public Function PlanExistingModelProperty(ByVal filePath As String, ByVal propertySetName As String, ByVal propertyName As String, ByVal existingValue As String, ByVal proposed As String) As PropertyChange
        Dim nextValue As String = ReplaceLeadingProjectPrefix(existingValue, proposed)
        If String.Equals(existingValue, nextValue, StringComparison.Ordinal) Then Return Nothing
        Return New PropertyChange With {
            .FilePath = filePath,
            .PropertySetName = propertySetName,
            .PropertyName = propertyName,
            .OldValue = existingValue,
            .NewValue = nextValue,
            .Reason = "Leading project prefix only"
        }
    End Function

    ' Typed drawing planner: explicitly named inputs prevent the historical
    ' filename/existing-value positional swap in the standalone candidate.
    ' Nothing is returned when identity is unverified or value is unchanged.
    Public Function PlanExistingDrawingProperty(ByVal filePath As String, ByVal filenameStem As String, ByVal existingDrawingNumber As String, ByVal targetProjectPrefix As String) As PropertyChange
        Dim nextValue As String = PlanDrawingNumber(existingValue:=existingDrawingNumber, fileBaseName:=filenameStem, proposed:=targetProjectPrefix)
        If String.Equals(existingDrawingNumber, nextValue, StringComparison.Ordinal) Then Return Nothing
        Return New PropertyChange With {
            .FilePath = filePath,
            .PropertySetName = "Inventor User Defined Properties",
            .PropertyName = "DRAWING_NUMBER",
            .OldValue = existingDrawingNumber,
            .NewValue = nextValue,
            .Reason = "Verified drawing identity and leading project prefix only"
        }
    End Function
End Module
