'' =====================================================================
' TRAVERSE_Through_Main_ASM_Relplcae_Old_Subs_With_New_Subs
' iLogic Rule: Rename & Replace Parts AND Sub-Assemblies (Recursive)
' + Derived Source Parts
' Last updated: 2026-11-04 (Fix: Phase 2 reuses identical file from prior pass instead of _Duplicate; ScanPrefixes PJ#####-only guard; Phase 4 oNameToNew built from oRenameMap actuals)
' (run from inside an ASSEMBLY)
'
' TWO MODES, chosen via a form at the start (see WHY TWO MODES below):
'   MODE 1 - PREFIX SWAP: file name must START WITH the find text.
'            Only the matched leading text is replaced; everything
'            after it is kept as-is. Use for swapping a whole project
'            code, e.g. Find 'PJ00195-3620', Replace 'PJ00195-3610'.
'   MODE 2 - SEGMENT REPLACE: file name must CONTAIN the find text
'            anywhere. Only that matched segment is swapped, wherever
'            it appears; the rest of the name is untouched. Use for
'            swapping a piece embedded mid-name, e.g. Find '3620',
'            Replace '3610' on 'PJ00195-3620-01-V01-08.iam'. Replace
'            may be left BLANK to strip the matched text out entirely -
'            e.g. Find '_DEL' with a blank Replace turns
'            'PartName_DEL_DEL.ipt' into 'PartName.ipt', removing every
'            occurrence of '_DEL' in one pass, not just the first.
'
'            Mode 2 now uses a Vault Copy Design-style multi-phase
'            approach so ONE run is enough (no more re-looping):
'              Phase 1 - build complete old->new map (no disk writes)
'              Phase 2 - copy every mapped file to its new name (olds kept)
'              Phase 3 - open each NEW assembly/part and rewrite its
'                        internal FileDescriptors + occurrences so they
'                        point at the other NEW files in the map
'              Phase 4 - repoint live session occurrences in the active tree
'              Phase 5 - leave olds on disk (safe); run Mode 5 to verify
'
' LOCALIZE WITHOUT RENAMING: enter the EXACT SAME text in Find and
' Replace (either mode). The computed "new" name is then identical to
' the old one, so nothing about the file name changes - but new copies
' still always land in the CURRENT ASSEMBLY'S folder, not wherever the
' matching sub currently lives. So a matching sub sitting in a
' different folder gets a local copy made (same name) and the
' occurrence repointed to it, while one already in this folder is left
' alone. Useful when Vault's Copy Design process (or similar) has
' already renamed a set of subs to the new project prefix, but they're
' still physically sitting in a different project's folder - this
' consolidates them locally without touching their names at all. This
' is a deliberately safe case for the self-match guard below (fix 6) -
' since the name never changes, there's nothing for a re-run to
' compound.
'
' WHY TWO MODES: these are genuinely different operations that used to
' be conflated into one "starts with" rule. Trying to use Mode 1's
' logic for a Mode 2 job (e.g. entering just 'PJ00195' as Find when you
' actually wanted to swap '3620') is what caused a real runaway-naming
' incident - the replace text still matched the find text afterward, so
' every re-run kept prepending another copy of it
' (e.g. "PJ00195-3610-3610-3610-..."). See fix 6 below.
'
' Other fixes layered on top from testing:
'   1. Case-insensitive matching in both modes.
'   2. Current-path-only cycle guard - a document used in more than one
'      place in the tree (a shared bracket, standard sub, etc.) is
'      normal and gets processed each time it's reached; it's only
'      flagged as a genuine cycle if it turns out to be its own
'      ancestor on the CURRENT path. The guard now removes its marker
'      when backing out of a branch, instead of leaving it forever.
'   3. Top-assembly self-reference safety check - since every renamed
'      file lands in the same top-level folder, a sub's computed new
'      name can coincidentally collide with the TOP ASSEMBLY'S OWN file
'      name. Repointing to it would silently create a circular
'      reference (a child occurrence pointing back at its own
'      ancestor). This is now explicitly checked and refused, with a
'      clear log entry, both for regular renames and derived-source
'      renames.
'   4. EXCLUSIONS - added after this rule was found to have renamed a
'      Content Center fastener with no protection against it. Anything
'      inside a Vault Library, Content Center Files\en-US folder, the
'      Jameson Cell SJD00-GT Standard folder, or flagged by Inventor as
'      a genuine Content Center member (regardless of where its file
'      physically lives) is now skipped entirely - never renamed, never
'      recursed into. Also excluded: anything already sitting directly
'      in THIS assembly's own "Non Std Parts" sub-folder (i.e. a direct
'      sibling of the current assembly's folder) - it's already been
'      correctly relocated there by the non-standard-parts mover rule.
'      A same-named "Non Std Parts" folder belonging to a DIFFERENT
'      project is deliberately NOT exempt - only the one directly under
'      the assembly currently being run counts as "official".
'   5. VIRTUAL COMPONENT HANDLING - a virtual component's FullFileName
'      legitimately matches whatever document currently hosts it (it
'      has no independent file). It's skipped entirely - never renamed,
'      and never recursed into either. An earlier version of this rule
'      tried to "look inside" a virtual assembly to find real nested
'      parts, but that caused a genuine infinite loop in testing: since
'      a virtual assembly's identity is shared with whatever hosts it,
'      recursing into it can mean re-entering that SAME level's own
'      occurrence list again - which includes the same virtual
'      component again, forever, until Inventor crashed. Skipping it
'      entirely is the only safe behaviour confirmed so far.
'   6. SELF-MATCH GUARD - warns and requires confirmation if the REPLACE
'      text starts with (Mode 1) or contains (Mode 2) the FIND text.
'      That combination means a renamed file could still match the find
'      text afterward, so re-running the rule (even by accident) could
'      keep compounding the same change indefinitely.
'   7. PERFORMANCE CACHE + DISK LOG - added after a run became very slow
'      and eventually crashed Inventor. The current-path cycle guard
'      (fix 2) correctly allows a shared component to be re-entered from
'      a different branch, but that meant its ENTIRE contents got
'      re-explored from scratch every single time - expensive in an
'      assembly with heavily reused components. Each document's explore
'      result (did anything inside it change) is now cached the first
'      time and reused on later encounters, restoring the original
'      speed. Separately, since an in-memory log is lost if Inventor
'      crashes outright, progress is now ALSO written to a timestamped
'      log file on the Desktop as the rule runs (entering/done per
'      document, before/after every SaveAs and Documents.Open) - if it
'      hangs or crashes, opening that file shows exactly what it was
'      doing at the time.
'   8. "Non Std Parts" AWARENESS - a sub currently sitting in a folder
'      named "Non Std Parts" (from ANY project) has its new copy routed
'      into THIS assembly's own "Non Std Parts" sub-folder instead of
'      the main folder, preserving that organizational split across the
'      relocation. Only a "Non Std Parts" folder that's a direct sibling
'      of the CURRENT assembly counts as already "official" and gets
'      excluded outright (fix 4) - a same-named folder elsewhere still
'      gets its contents relocated, just to the right place.
'   9. CHECKED-IN/READ-ONLY HANDLING - the top assembly's read-only
'      status is checked BEFORE any work starts, warning if it looks
'      checked-in rather than running the whole traversal only to fail
'      on the final save. The same check now also runs before every
'      in-place Save() on an intermediate sub-assembly or a part whose
'      derived source changed - a checked-in file there is skipped with
'      a clear log entry instead of attempting a save that can trigger
'      Inventor's own native error dialog (which Try/Catch alone cannot
'      suppress). A skipped file's reference update only exists in
'      memory until that specific file is checked out and saved by hand.
'  10. DECISIONS LOG - the timing log (fix 7) only ever recorded WHEN
'      something was entered/checked, not WHAT was decided about it
'      (matched and renamed, excluded, safety-skipped, etc.) - that
'      reasoning lived only in memory until the final summary popup, so
'      a run that needed diagnosing from disk alone (no popup available)
'      couldn't actually explain a "why wasn't this renamed" question.
'      A second file, "<timing log name>_Decisions.txt", is now written
'      alongside the timing log and updated after every single occurrence
'      is processed, containing the exact same detail as the final
'      popup - so it's available on disk even if the run is still going,
'      hangs, or the popup is never seen.
'
' What it does:
'   1. Looks at the current ACTIVE assembly and its folder location.
'   2. Asks which mode, and the find/replace text, via one form.
'   3. Walks the ENTIRE assembly tree, bottom-up:
'        - For every part/sub-assembly whose file name STARTS WITH the
'          "find" text: if a file with the NEW name already exists in
'          the assembly folder, just points the occurrence at it. If
'          not, saves a renamed COPY into the main assembly's folder
'          (original file untouched) and swaps every reference to it
'          over to the new copy.
'        - For EVERY PART encountered (whether or not the part itself
'          gets renamed), its DERIVED SOURCE file (if any) is checked
'          the same way - this is what closes the gap where a derived
'          source isn't placed anywhere as its own occurrence, so the
'          plain occurrence walk would otherwise never find it.
'        - For a sub-assembly whose OWN name does NOT match, but which
'          contains something below it that DID get renamed: that
'          sub-assembly/part is saved IN PLACE (same filename,
'          overwritten) so its internal references stay correct.
'        - A SECOND PASS at each level repoints any additional raw
'          occurrence (e.g. a Component Pattern instance) that shares a
'          file with something already renamed this run - these are
'          never the "representative" occurrence picked for the main
'          loop, so without this pass they'd stay pointing at the OLD
'          file forever.
'        - Anything untouched by the find/replace (e.g. shared/library
'          parts) is left completely alone.
'   4. Saves the main assembly with its updated references.
'
' WHY BOTTOM-UP: if a part inside a sub-assembly gets renamed, the
' sub-assembly that contains it MUST be updated to point at the new
' file, or its internal reference breaks. So children (and, for parts,
' their derived source) are always processed before the part/assembly
' that references them.
'
' NOTE: derive chains are chased recursively - if the derived source
' part is itself derived from something else, that grandparent source
' is also repointed (using oRenameMap dedup to prevent loops).
'
' CAUTION: this can overwrite sub-assembly/part files IN PLACE (the
' "name unchanged but contents changed" case) and can open derived
' source documents not already loaded in the session - test on a COPY
' of your project folder before running this on live data.
' =====================================================================

' ---------------------------------------------------------------------
' MODE 4 HELPERS
' ---------------------------------------------------------------------

' Scans all documents in the tree via AllReferencedDocuments and returns
' a sorted list of unique P-prefixed project tokens found in filenames,
' each paired with a count of how many distinct files carry that token.
' A token is defined as everything from the start of the filename up to
' (but not including) the first "-" or "_", when the filename starts with
' "P" (case-insensitive). Excluded and virtual files are skipped.
' Returns a List(Of String) of "TOKEN|COUNT" strings, sorted by token.

' Shows a form listing the scanned P-prefixed tokens with file counts.
' User selects which ones to target (ALL button, individual checkboxes)
' and enters the new project number. Returns the list of selected Find
' tokens and the Replace text via the passed-in RenameModeChoice object.
' Returns True if the user confirmed, False if cancelled.
Sub Main()

    ' ══════════════════════════════════════════════════════════════════════
    ' PRESET RENAME MAP — one-shot override for non-standard naming schemes.
    ' When oPresetMap has entries the DrawingModelRenameForm is skipped and
    ' these exact basenames (no extension) are used instead of the auto-
    ' generated prefix-swap names.
    '
    ' HOW TO USE:
    '   1. Set USE_PRESET_MAP = True
    '   2. Uncomment & fill the oPresetMap.Add() lines below (or add more)
    '      Key   = OLD model basename WITHOUT extension (as it appears on disk)
    '      Value = NEW model basename WITHOUT extension
    '   3. Run the rule from the GA assembly as normal
    '   4. When done: set USE_PRESET_MAP = False and comment the lines back out
    '
    ' NOTE: files NOT in this map are renamed by the normal prefix-swap rules.
    ' ══════════════════════════════════════════════════════════════════════
    Dim USE_PRESET_MAP As Boolean = True   ' *** set False when done ***
    Dim oPresetMap As System.Collections.Generic.Dictionary(Of String, String) = Nothing
    If USE_PRESET_MAP Then
        oPresetMap = New System.Collections.Generic.Dictionary(Of String, String)(StringComparer.OrdinalIgnoreCase)
        ' ── PJ00205 E3432-8 one-shot entries (generated 2026-11-03) ─────
        ' Format: oPresetMap.Add("OLD-BASENAME-NO-EXT", "NEW-BASENAME-NO-EXT")
        oPresetMap.Add("PJ00161-E3432-8-NEW E8 TOP GENERAL ASSEMBLY_WIP", "PJ00205-3450-001-V01-00")
        oPresetMap.Add("PJ00161-E3432-8-NEW E8 TOP GENERAL ASSEMBLY",     "PJ00205-3450-001-V01-00")
        oPresetMap.Add("PJ00161-E3432-8-Name Plate_2",                    "PJ00205-E3432-8-Name Plate_2")
        oPresetMap.Add("PJ00161-E3432-8-TANK UPPER ASSEMBLY",             "PJ00205-3450-110-V01-00")
        oPresetMap.Add("PJ00161-E3432-8-TANK ASSEMBLY",                   "PJ00205-3450-400-V01-00")
        oPresetMap.Add("PJ00161-E3432-8-TANK ASSEMBLY TRANSPORT",         "PJ00205-3450-400-V00-00")
        oPresetMap.Add("PJ00161-E3432-8-DOWNCOMER ASSEMBLY",              "PJ00205-3450-120-V05-00")
        oPresetMap.Add("PJ00161-E3432-8-WASH WATER SYSTEM",               "PJ00205-3450-130-V01-00")
        oPresetMap.Add("PJ00161-E3432-8-V0-03-002",                       "PJ00205-3450-130-V01-10-001")
        oPresetMap.Add("PJ00141-345-xx-V0-03-003",                        "PJ00205-3450-130-V01-10")
        oPresetMap.Add("PJ00141-345-xx-V0-03-002",                        "PJ00205-3450-130-V01-11")
        oPresetMap.Add("PJ00161-E3432-8-GRATING",                         "PJ00205-3450-150-V01-01")
        oPresetMap.Add("PJ00161-E3432-8-HANDRAIL ASSY",                   "PJ00205-3450-160-V01-00")
        oPresetMap.Add("PJ00161-E3432-8-28",                              "PJ00205-3450-120-V01-01")
        oPresetMap.Add("PJ00161-E3432-8-29",                              "PJ00205-3450-120-V01-011")
        oPresetMap.Add("PJ00161-E3432-8-V0-10-001",                       "PJ00205-3450-900-V01-00")
        oPresetMap.Add("PJ00161-E3432-8-V0-10-002",                       "PJ00205-3450-900-V01-01")
        oPresetMap.Add("PJ00161-E3432-8-32",                              "PJ00205-3450-800-V01-001")
        oPresetMap.Add("PJ00161-E3432-8-175",                             "PJ00205-3450-800-V01-002")
        oPresetMap.Add("PJ00161-E3432-8-55",                              "PJ00205-3450-400-V02-00")
        oPresetMap.Add("PJ00161-E3432-8-57",                              "PJ00205-3450-400-V03-00")
        oPresetMap.Add("PJ00161-E3432-8-56",                              "PJ00205-3450-400-V04-00")
        oPresetMap.Add("PJ00161-E3432-8-58",                              "PJ00205-3450-400-V05-00")
        oPresetMap.Add("PJ00161-E3432-8-53",                              "PJ00205-3450-110-V02-00")
        oPresetMap.Add("PJ00161-E3432-8-TANK MODULE 1",                   "PJ00205-3450-400-V01-001")
        oPresetMap.Add("PJ00161-E3432-8-TANK GUSSET",                     "PJ00205-3450-400-V01-002")
        oPresetMap.Add("PJ00161-E3432-8-TANK GUSSET 2",                   "PJ00205-3450-400-V01-003")
        oPresetMap.Add("PJ00161-E3432-8-TANK GUSSET 3",                   "PJ00205-3450-400-V01-004")
        oPresetMap.Add("PJ00161-E3432-8-TANK MODULE 2",                   "PJ00205-3450-400-V02-001")
        oPresetMap.Add("PJ00161-E3432-8-TANK MODULE 3",                   "PJ00205-3450-400-V03-001")
        oPresetMap.Add("PJ00161-E3432-8-TANK MODULE 4",                   "PJ00205-3450-400-V04-001")
        oPresetMap.Add("PJ00161-E3432-8-PIPE SPOOL",                      "PJ00205-3450-120-V01-002")
        oPresetMap.Add("PJ00161-E3432-8-V0-07-001",                       "PJ00205-3450-120-V01-003")
        oPresetMap.Add("PJ00161-E3432-8-V0",                              "PJ00205-3450-120-V01-004")
        oPresetMap.Add("PJ00161-E3432-8-TANK PLATFORM ASSEMBLY",          "PJ00205-3450-320-V01-01")
        oPresetMap.Add("PJ00161-E3432-8-UPPER FRAME",                     "PJ00205-3450-320-V01-02")
        oPresetMap.Add("PJ00161-E3432-8-TANK BLIND FLANGE",               "PJ00205-3450-400-V05-008")
        oPresetMap.Add("PJ00161-E3432-8-WASH WATER TRAY-SS",              "PJ00205-3450-130-V01-001")
        oPresetMap.Add("PJ00161-E3432-8-V0-03-007",                       "PJ00205-3450-130-V02-00")
        oPresetMap.Add("PJ00161-E3432-8-60",                              "PJ00205-3450-340-V01-001")
        oPresetMap.Add("PJ00161-E3432-8-51",                              "PJ00205-3450-340-V01-002")
        oPresetMap.Add("PJ00161-E3432-8-54",                              "PJ00205-3450-340-V01-003")
        oPresetMap.Add("PJ00161-E3432-8-20",                              "PJ00205-3450-400-V05-001")
        oPresetMap.Add("PJ00161-E3432-8-47",                              "PJ00205-3450-400-V05-002")
        oPresetMap.Add("PJ00161-E3432-8-70",                              "PJ00205-3450-400-V05-003")
        oPresetMap.Add("PJ00161-E3432-8-71",                              "PJ00205-3450-400-V05-004")
        oPresetMap.Add("PJ00161-E3432-8-165",                             "PJ00205-3450-400-V05-005")
        oPresetMap.Add("PJ00161-E3432-8-167",                             "PJ00205-3450-400-V05-006")
        oPresetMap.Add("PJ00161-E3432-8-73",                              "PJ00205-3450-400-V05-007")
        oPresetMap.Add("PJ00161-E3432-8-30",                              "PJ00205-3450-120-V02-01")
        oPresetMap.Add("PJ00161-E3432-8-V0-10-001-020_MIR",               "PJ00205-3450-900-V02-001")
        ' DUPLICATE KEY REMOVED: PJ00161-E3432-8-V0-10-001 already mapped at line 246 → PJ00205-3450-900-V01-00
        oPresetMap.Add("PJ00161-E3432-8-V0-10-003",                       "PJ00205-3450-900-V01-002")
        oPresetMap.Add("PJ00165-346-xx-V0-01_ReferenceCopy",              "PJ00205-346-xx-V0-01_ReferenceCopy")
        ' ────────────────────────────────────────────────────────────────
    End If

    ' ---------- Basic checks ----------
    Dim oAsmDoc As AssemblyDocument
    Try
        Dim oActiveDoc As Document = ThisApplication.ActiveDocument
        If oActiveDoc Is Nothing Then
            MessageBox.Show("Could not get the active document.", "Error")
            Exit Sub
        End If

        ' ── AUTO-ROUTE BY DOCUMENT TYPE ────────────────────────────────────
        ' Drawing → Drawing Copy Mode first; offers Full Sweep at end.
        ' Assembly → straight to full assembly traverse.
        If oActiveDoc.DocumentType = kDrawingDocumentObject Then
            Dim oDwgDocMain As DrawingDocument = CType(oActiveDoc, DrawingDocument)
            RunDrawingCopyMode(oDwgDocMain, oPresetMap)
            Exit Sub
        ElseIf oActiveDoc.DocumentType = kAssemblyDocumentObject Then
            oAsmDoc = CType(oActiveDoc, AssemblyDocument)
        Else
            MessageBox.Show("This rule must be run from the GA assembly or its GA drawing.", "Wrong Document Type")
            Exit Sub
        End If
    Catch ex As Exception
        MessageBox.Show("Could not get the active document: " & ex.Message, "Error")
        Exit Sub
    End Try

    RunAssemblyTraverseMode(oAsmDoc, oPresetModelRenameMap:=oPresetMap)

End Sub

' =====================================================================
' ASSEMBLY TRAVERSE MODE
' Called from Main() when active doc is an assembly, or from
' RunDrawingCopyMode when the user opts for the full Clean Sweep.
' =====================================================================
Sub RunAssemblyTraverseMode(oAsmDoc As AssemblyDocument, Optional sPresetTargetFolder As String = "", Optional sPresetOldPrefix As String = "", _
    Optional oPresetModelRenameMap As System.Collections.Generic.Dictionary(Of String, String) = Nothing)

    ' ---------- Read-only check REMOVED 2026-10-28 ----------
    ' In the Copy Design / New Drawing workflow the source GA is ALWAYS checked
    ' in to Vault (read-only on disk) when this rule starts. That is correct and
    ' expected: the rule only TRAVERSES the source tree and SaveAs-copies every
    ' component to a new path. It never saves back to the source GA.
    ' The old Yes/No dialog was firing every single run as a false positive.
    ' Any genuine save failure on the NEW copies is caught by the end-of-run
    ' save handler further below — no upfront check needed here.

    ' ---------- Keep a reference to the originating GA drawing (if any) ----------
    ' Inventor's SaveAs() activates the newly saved document, so the GA drawing
    ' window gets pushed to background during the traverse and appears to close.
    ' We capture it here and re-activate it once the traverse is complete.
    Dim oOriginatingDrawing As DrawingDocument = Nothing
    Try
        Dim oStartDoc As Document = ThisApplication.ActiveDocument
        If oStartDoc IsNot Nothing AndAlso oStartDoc.DocumentType = kDrawingDocumentObject Then
            oOriginatingDrawing = CType(oStartDoc, DrawingDocument)
        End If
    Catch
        ' Not critical — if we can't capture it, we just won't re-activate.
    End Try

    Dim oAsmDef As AssemblyComponentDefinition = oAsmDoc.ComponentDefinition
    ' Use the assembly's own folder as the target — ThisDoc.Path would point
    ' to the drawing folder if the rule was launched from a drawing.
    Dim sTopAssemblyFullName As String = oAsmDoc.FullFileName
    Dim sTargetFolder As String = System.IO.Path.GetDirectoryName(sTopAssemblyFullName)
    Dim oLog As New System.Text.StringBuilder()
    Dim iCount As Integer = 0

    ' ---------- Capture original assembly state (FIRST RUN ONLY) ----------
    ' Snapshot of every occurrence's ORIGINAL file, so the assembly can be
    ' reverted later if this rule (or a later run of it) doesn't produce
    ' the desired result. Skipped entirely if the snapshot already exists
    ' for this assembly - it must never be overwritten by a later run,
    ' since the whole point is to preserve the TRUE starting state, not
    ' whatever the tree looks like after some renaming has already
    ' happened. This works because SaveAs(newName, True) never deletes or
    ' modifies the original file - only a new copy is created - so the
    ' file recorded here should still exist on disk even after this rule
    ' has renamed things.
    Dim sSnapshotPath As String = System.IO.Path.Combine(sTargetFolder, System.IO.Path.GetFileNameWithoutExtension(sTopAssemblyFullName) & "_Original_Featured_Files_Folder_Location.txt")
    If Not System.IO.File.Exists(sSnapshotPath) Then
        Try
            CaptureOriginalState(oAsmDoc, sSnapshotPath)
        Catch ex As Exception
            MessageBox.Show("Could not write the original-state snapshot (continuing anyway):" & vbCrLf & ex.Message, "Snapshot Warning")
        End Try
    End If

    ' ---------- Disk-flushed crash log ----------
    ' Written to as we go (not just shown in the final popup), so if
    ' Inventor crashes mid-run, opening this file afterward shows exactly
    ' what was happening right before it went down.
    Dim dRuleStartTime As DateTime = DateTime.Now
    Dim sLogFilePath As String = System.Environment.GetFolderPath(System.Environment.SpecialFolder.Desktop) & "\Traverse_Rename_Log_" & DateTime.Now.ToString("yyyy-MM-dd_HHmmss") & ".txt"
    Try
        System.IO.File.WriteAllText(sLogFilePath, "TRAVERSE_Through_Main_ASM_Relplcae_Old_Subs_With_New_Subs" & vbCrLf & "Rule built: 2026-10-29 Mode6-FullTreeScan-AnomalyPrefill-v18 (drawing FD fix + BC fallback + FIX3 cross-project derived pass)" & vbCrLf & "Rule started: " & DateTime.Now.ToString() & vbCrLf & "Top assembly: " & sTopAssemblyFullName & vbCrLf)
    Catch
        ' If the log file can't even be created, carry on anyway - the
        ' final in-memory summary popup still works as a fallback.
    End Try

    ' ---------- This rule always runs the Copy Design / Drawing workflow ----------
    ' Mode picker removed 2026-10-28: this variant is purpose-built for the
    ' "run from a GA drawing" workflow. It always does a full batch-rename TRAVERSE
    ' followed by a drawing reference repoint. No mode selection needed.
    Dim oChoice As New RenameModeChoice()
    oChoice.bCopyDesignMode = True
    oChoice.bUpdateDrawings = True   ' drawing repoint is always on for this rule

    ' Auto-detect drawings folder from the GA drawing that is currently open.
    ' ThisDoc.Path gives the folder of the drawing the rule was launched from.
    ' oAsmDoc.FullFileName gives the source assembly the drawing references.
    ' The drawings folder is the folder containing the open GA drawing.
    Dim sDrawingsFolderAuto As String = ""
    Try
        ' ThisDoc is the iLogic ICadDoc host; .Document gives the Inventor Document object.
        sDrawingsFolderAuto = System.IO.Path.GetDirectoryName(ThisDoc.Document.FullFileName)
    Catch
        ' If launched from the assembly directly rather than a drawing, fall
        ' back to the assembly's own folder — Phase 0 will find nothing but
        ' the rule still works without drawings.
        sDrawingsFolderAuto = System.IO.Path.GetDirectoryName(sTopAssemblyFullName)
    End Try
    oChoice.sDrawingsFolder = sDrawingsFolderAuto

    Dim sFind As String = oChoice.sFind
    Dim sReplace As String = oChoice.sReplace
    Dim bUseContainsMode As Boolean = oChoice.bUseContainsMode
    Dim bMode2MultiPhaseDone As Boolean = False



    ' ---------- Turn off Inventor's confirmation dialogs while we work ----------
    ResetExitFlag()
    Dim oExcelApp As Object = Nothing
    Dim bExcelAlertsOriginal As Boolean = True
    Dim bExcelCreatedHere As Boolean = False
    Try
        oExcelApp = GetObject(, "Excel.Application")
        bExcelAlertsOriginal = oExcelApp.DisplayAlerts
        oExcelApp.DisplayAlerts = False
    Catch
        Try
            oExcelApp = CreateObject("Excel.Application")
            oExcelApp.Visible = False
            oExcelApp.DisplayAlerts = False
            bExcelCreatedHere = True
        Catch
            oExcelApp = Nothing
        End Try
    End Try
    GetSetExcelApp(True, oExcelApp)
    Dim bOrigSilent As Boolean = ThisApplication.SilentOperation
    ThisApplication.SilentOperation = True

    ' Snapshot documents already open BEFORE we start opening anything.
    ' Used by OpenDocTracked / CloseIfOpenedHere / final cleanup so the rule
    ' does not leave hundreds of Documents.Open() results resident in memory
    ' for the whole run (the main cause of 800MB -> 3.5GB freezes).
    SnapshotInitiallyOpenDocuments()

    ' Tracks every file already renamed/consolidated this run (old full name -> new full name).
    Dim oRenameMap As New System.Collections.Generic.Dictionary(Of String, String)
    ' Accumulates assembly files whose linked param tables could not be updated
    ' because they are checked in to Vault (read-only / COM-intercepted). Shown
    ' in a dedicated popup after the run so the user knows exactly what to check out.
    Dim oNeedsCheckout As New System.Collections.Generic.HashSet(Of String)
    ' Tracks files already re-saved in place this run, so a shared sub-assembly
    ' referenced from multiple parents isn't saved over and over.
    Dim oSavedInPlace As New System.Collections.Generic.HashSet(Of String)
    ' Cycle guard - CURRENT PATH only (see header note above).
    Dim oVisitedLevels As New System.Collections.Generic.HashSet(Of String)
    ' Ordered mirror of oVisitedLevels, purely for diagnostic messages if a
    ' genuine cycle is ever hit (shows the full chain of parents involved).
    Dim oPathStack As New System.Collections.Generic.List(Of String)
    ' PERFORMANCE: caches the True/False result of fully exploring each
    ' document (did anything inside it change), keyed by its full file
    ' name. Without this, a shared sub-assembly reached from multiple
    ' parent branches gets its ENTIRE contents re-explored from scratch
    ' every single time - the current-path cycle guard correctly allows
    ' this (it's not a real cycle), but redoing the full traversal is
    ' pure waste once we already know the answer for that document this
    ' run. This is what keeps a heavily-reused-component assembly fast.
    ' (Mode 3 does not use this cache - see ConsolidateLevel.)
    Dim oProcessedResults As New System.Collections.Generic.Dictionary(Of String, Boolean)
    ' Phase 0 drawing scan result — hoisted to Sub Main scope so it is visible
    ' both inside the Mode 6 block (where it is populated) and later at the
    ' drawing selection form call site.
    Dim oPhase0Data As System.Collections.Generic.List(Of Object()) = Nothing

    ' ---------- MODE 6: Copy Design (Vault-style one-pass) ----------
    ' Combines prefix swap + optional segment replaces + non-std localization
    ' into ONE master map, then runs the Mode 2 multi-phase engine once.
    If oChoice.bCopyDesignMode Then

        ' ══════════════════════════════════════════════════════════════════════
        ' STEP 1 — Select folder for new GA model copies
        ' ══════════════════════════════════════════════════════════════════════
        ' The first and only folder prompt. The drawings folder is auto-detected
        ' above from the open GA drawing. Here we just ask WHERE the renamed
        ' model copies should land. Pre-seed from last choice, then drawings
        ' folder (one click across to the models folder), then source asm folder.
        ' If a target folder was pre-supplied (e.g. called from Drawing Copy Mode),
        ' skip the picker entirely — the GA is already in the right folder.
        If Trim(sPresetTargetFolder) <> "" AndAlso System.IO.Directory.Exists(sPresetTargetFolder) Then
            sTargetFolder = sPresetTargetFolder
            oChoice.sTargetFolder = sTargetFolder
        Else
            Dim oFbdTarget As New FolderBrowserDialog()
            oFbdTarget.Description = "STEP 1 of 3 — Select folder for new GA model copies  (all renamed sub copies land here)"
            Dim sSeedTarget As String = If(Trim(oChoice.sTargetFolder) <> "", oChoice.sTargetFolder, _
                                           If(Trim(oChoice.sDrawingsFolder) <> "", oChoice.sDrawingsFolder, _
                                              System.IO.Path.GetDirectoryName(sTopAssemblyFullName)))
            If System.IO.Directory.Exists(sSeedTarget) Then oFbdTarget.SelectedPath = sSeedTarget
            If oFbdTarget.ShowDialog() <> DialogResult.OK Then
                MessageBox.Show("Cancelled - no changes made.", "Cancelled")
                ThisApplication.SilentOperation = bOrigSilent
                Exit Sub
            End If
            sTargetFolder = oFbdTarget.SelectedPath
            oChoice.sTargetFolder = sTargetFolder
        End If
        If Not System.IO.Directory.Exists(sTargetFolder) Then
            Try
                System.IO.Directory.CreateDirectory(sTargetFolder)
            Catch exMk As Exception
                MessageBox.Show("Could not create target folder: " & exMk.Message, "Error")
                ThisApplication.SilentOperation = bOrigSilent
                Exit Sub
            End Try
        End If

        ' ══════════════════════════════════════════════════════════════════════
        ' STEP 2 — Config form: new prefix, segment rules, folder structure
        ' ══════════════════════════════════════════════════════════════════════
        ' MUST run BEFORE the Drawing Model Rename form so oChoice.sReplace is
        ' populated and the rename grid can pre-fill the correct new names.
        '
        ' RE-RUN DETECTION: if the target folder already contains a renamed copy
        ' of the GA (from a previous partial run), lock the new-prefix field so
        ' the user cannot accidentally drift to a different prefix mid-process.
        Try
            Dim sGaBase As String = System.IO.Path.GetFileNameWithoutExtension(sTopAssemblyFullName)
            Dim sGaExt As String = System.IO.Path.GetExtension(sTopAssemblyFullName)
            Dim iGaDash As Integer = sGaBase.IndexOf("-"c)
            If iGaDash > 0 AndAlso System.IO.Directory.Exists(sTargetFolder) Then
                Dim sGaSuffix As String = sGaBase.Substring(iGaDash) & sGaExt
                Dim sGaSuffixUpper As String = sGaSuffix.ToUpper()
                For Each sExisting As String In System.IO.Directory.GetFiles(sTargetFolder, "*" & sGaExt)
                    Dim sExBase As String = System.IO.Path.GetFileName(sExisting)
                    If sExBase.ToUpper().EndsWith(sGaSuffixUpper) Then
                        Dim iExDash As Integer = sExBase.IndexOf("-"c)
                        If iExDash > 0 Then
                            Dim sDetectedPrefix As String = sExBase.Substring(0, iExDash)
                            If Trim(sDetectedPrefix) <> "" Then
                                oChoice.sReplace = sDetectedPrefix
                                oChoice.bPrefixLocked = True
                            End If
                        End If
                        Exit For
                    End If
                Next
            End If
        Catch
        End Try
        If Not ShowCopyDesignConfigForm(oChoice, sTopAssemblyFullName) Then
            MessageBox.Show("Cancelled - no changes made.", "Cancelled")
            ThisApplication.SilentOperation = bOrigSilent
            Exit Sub
        End If
        sReplace = oChoice.sReplace
        ' sTargetFolder already set from Step 1 — never override from oChoice.sTargetFolder here

        ' ══════════════════════════════════════════════════════════════════════
        ' STEP 3 — Phase 0 silent scan + Drawing Model Rename form
        ' ══════════════════════════════════════════════════════════════════════
        ' Runs AFTER the config form so oChoice.sReplace is set and the rename
        ' grid pre-fills new model names with the correct new prefix.
        ' SKIP when called from Drawing Copy Mode Full Sweep — drawings were
        ' already processed by RunDrawingCopyMode; showing this form again is
        ' redundant and confusing.
        ' ── PRE-LOAD PRESET MAP — runs before the form, not instead of it ──
        ' When oPresetModelRenameMap is supplied, seed oChoice.oExplicitModelRenameMap
        ' with the caller's specific old->new basenames BEFORE the form opens.
        ' ShowDrawingModelRenameForm checks oExplicitModelRenameMap first when
        ' pre-filling each editable field, so the user sees our numbered names
        ' instead of the auto-generated prefix-swap names — and can still edit them.
        If oPresetModelRenameMap IsNot Nothing AndAlso oPresetModelRenameMap.Count > 0 Then
            For Each kvp As System.Collections.Generic.KeyValuePair(Of String, String) In oPresetModelRenameMap
                oChoice.oExplicitModelRenameMap(kvp.Key) = kvp.Value
            Next
            oLog.Append(vbCrLf & "PRESET-MAP: " & oPresetModelRenameMap.Count & " model renames pre-loaded into form defaults")
            Try : System.IO.File.AppendAllText(sLogFilePath, "PRESET-MAP: " & oPresetModelRenameMap.Count & " model renames pre-loaded" & vbCrLf) : Catch : End Try
        End If

        If Trim(sPresetOldPrefix) <> "" AndAlso (oPresetModelRenameMap Is Nothing OrElse oPresetModelRenameMap.Count = 0) Then
            ' Full-sweep path (called from RunDrawingCopyMode without a preset map):
            ' drawings already processed — skip the rename form entirely.
            oLog.Append(vbCrLf & "FULL-SWEEP: Drawing rename form skipped (drawings already processed by Drawing Copy Mode)")
            Try : System.IO.File.AppendAllText(sLogFilePath, "FULL-SWEEP: Drawing rename form skipped" & vbCrLf) : Catch : End Try
            oChoice.bUpdateDrawings = False
        ElseIf Trim(oChoice.sDrawingsFolder) <> "" AndAlso System.IO.Directory.Exists(oChoice.sDrawingsFolder) Then
            Dim bOrigSilentP0 As Boolean = ThisApplication.SilentOperation
            ThisApplication.SilentOperation = True
            Try
                oPhase0Data = RunPhase0DrawingScan(oChoice.sDrawingsFolder, oLog, sLogFilePath)
            Catch ex As Exception
                oLog.Append(vbCrLf & "PHASE0 SCAN FAILED: " & ex.Message)
            Finally
                ThisApplication.SilentOperation = bOrigSilentP0
            End Try

            If oPhase0Data IsNot Nothing AndAlso oPhase0Data.Count > 0 Then
                If Not ShowDrawingModelRenameForm(oChoice, oPhase0Data) Then
                    MessageBox.Show("Cancelled - no changes made.", "Cancelled")
                    ThisApplication.SilentOperation = bOrigSilent
                    Exit Sub
                End If
                oLog.Append(vbCrLf & "Drawing model renames: " & oChoice.oExplicitModelRenameMap.Count & " model(s) explicitly mapped")
            Else
                oLog.Append(vbCrLf & "Phase 0: no .idw files found in drawings folder — drawing repoint will be skipped")
                oChoice.bUpdateDrawings = False
            End If
            Try
                System.IO.File.AppendAllText(sLogFilePath, oLog & vbCrLf)
            Catch
            End Try
        Else
            oLog.Append(vbCrLf & "Phase 0: drawings folder not found — drawing repoint will be skipped")
            oChoice.bUpdateDrawings = False
        End If  ' End of sPresetOldPrefix guard (If/ElseIf/Else block)

        ' ══════════════════════════════════════════════════════════════════════
        ' STEP 4 — Old prefix token scan + confirmation
        ' When called from Drawing Copy Mode Full Sweep, the old prefix and new
        ' prefix are already known — skip the batch selection form entirely and
        ' wire them in directly so we never hit the "old = new" abort guard.
        ' ══════════════════════════════════════════════════════════════════════
        If Trim(sPresetOldPrefix) <> "" Then
            ' Pre-supplied by Full Sweep caller — still scan the full tree so
            ' cross-project prefixes (PJ00180, PJ00190, etc.) are not missed.
            If oChoice.oBatchFinds Is Nothing Then
                oChoice.oBatchFinds = New System.Collections.Generic.List(Of String)()
            End If
            oChoice.oBatchFinds.Clear()
            oChoice.oBatchFinds.Add(Trim(sPresetOldPrefix))
            Try
                Dim oExtraTokens As System.Collections.Generic.List(Of String) = ScanPrefixes(oAsmDoc)
                Dim iAdded As Integer = 0
                For Each sTokLine As String In oExtraTokens
                    Dim sTok As String = sTokLine
                    Dim iPipe As Integer = sTokLine.IndexOf("|"c)
                    If iPipe > 0 Then sTok = sTokLine.Substring(0, iPipe)
                    sTok = Trim(sTok)
                    If sTok = "" Then Continue For
                    If String.Compare(sTok, sPresetOldPrefix, True) = 0 Then Continue For
                    If String.Compare(sTok, sReplace, True) = 0 Then Continue For
                    If Not oChoice.oBatchFinds.Contains(sTok) Then
                        oChoice.oBatchFinds.Add(sTok)
                        iAdded += 1
                    End If
                Next
                Try : System.IO.File.AppendAllText(sLogFilePath, "FULL-SWEEP: added " & iAdded & " extra prefix(es) from full-tree scan: " & String.Join(", ", oChoice.oBatchFinds) & vbCrLf) : Catch : End Try
            Catch exScan As Exception
                Try : System.IO.File.AppendAllText(sLogFilePath, "FULL-SWEEP: extra prefix scan failed (" & exScan.Message & ") - continuing with preset only" & vbCrLf) : Catch : End Try
            End Try
            ' sReplace is already set from the config form (Step 2) — no change needed
            Try : System.IO.File.AppendAllText(sLogFilePath, "FULL-SWEEP: old prefix pre-supplied = '" & Trim(sPresetOldPrefix) & "'  new prefix = '" & sReplace & "'" & vbCrLf) : Catch : End Try
        Else
            Dim oCdTokens As System.Collections.Generic.List(Of String)
            Try
                oCdTokens = ScanPrefixes(oAsmDoc)
            Catch ex As Exception
                MessageBox.Show("Prefix scan failed: " & ex.Message, "Copy Design")
                ThisApplication.SilentOperation = bOrigSilent
                Exit Sub
            End Try
            If Not ShowBatchSelectionForm(oCdTokens, oChoice) Then
                MessageBox.Show("Cancelled - no changes made.", "Cancelled")
                ThisApplication.SilentOperation = bOrigSilent
                Exit Sub
            End If
            sReplace = oChoice.sReplace
        End If

        Dim sNonStdFolder As String = System.IO.Path.Combine(sTargetFolder, "Non Std Parts")
        If oChoice.bLocalizeNonStd Then
            Try
                If Not System.IO.Directory.Exists(sNonStdFolder) Then System.IO.Directory.CreateDirectory(sNonStdFolder)
            Catch ex As Exception
                MessageBox.Show("Could not create Non Std Parts folder: " & ex.Message, "Copy Design")
                ThisApplication.SilentOperation = bOrigSilent
                Exit Sub
            End Try
        End If

        Dim oCdMap As System.Collections.Generic.Dictionary(Of String, String) = _
            BuildCopyDesignRenameMap(oAsmDoc, oChoice.oBatchFinds, sReplace, _
                oChoice.oSegFinds, oChoice.oSegReplaces, oChoice.bLocalizeNonStd, _
                oChoice.bHonourFolderStructure, _
                sTargetFolder, sTopAssemblyFullName, sNonStdFolder, _
                oChoice.oExplicitModelRenameMap, oLog, sLogFilePath)

        If oCdMap Is Nothing OrElse oCdMap.Count = 0 Then
            MessageBox.Show("Copy Design map is empty - nothing to do.", "Copy Design")
            ThisApplication.SilentOperation = bOrigSilent
            Exit Sub
        End If

        ' ══════════════════════════════════════════════════════════════════════
        ' INJECT TOP ASSEMBLY INTO COPY DESIGN MAP
        ' BuildCopyDesignRenameMap deliberately skips sTopAssemblyFullName.
        ' We compute its new path here using the same prefix-swap + segment
        ' rules, then add it so Phase 2 File.Copy's it, Phase 3 fixes its
        ' internal refs, and Phase 4 only opens and repoints the NEW copy.
        ' The original top assembly is protected by IsDocSafeToMutate: it sits
        ' in the OLD project folder, so it returns False and Phase 4 skips it.
        ' ══════════════════════════════════════════════════════════════════════
        Dim sTopAsmOldBase As String = System.IO.Path.GetFileNameWithoutExtension(sTopAssemblyFullName)
        Dim sTopAsmExt As String = System.IO.Path.GetExtension(sTopAssemblyFullName)
        Dim sTopAsmNewBase As String = sTopAsmOldBase
        Dim iTPSeg As Integer
        Dim sSFTP As String = ""
        Dim sSRTP As String = ""
        Dim sTopAsmNewFull As String = ""
        ' 1) Prefix swap - extract old prefix from the GA filename (everything before
        '    the first '-'), then replace with sReplace.
        '    EXCEPTION: when called from Full Sweep the GA is already renamed (old prefix
        '    is already gone from the filename). In that case sPresetOldPrefix carries the
        '    original old prefix and we use it directly to build the new name, bypassing
        '    the filename-derived check which would give old=new and abort.
        Dim iFirstDash As Integer = sTopAsmOldBase.IndexOf("-"c)
        If iFirstDash > 0 Then
            Dim sTopOldPrefix As String = sTopAsmOldBase.Substring(0, iFirstDash)
            If Trim(sPresetOldPrefix) <> "" Then
                ' Full Sweep path: GA already renamed — use preset old prefix to swap
                ' e.g. "PJ00222-3450-6-V0-00" with old=PJ00193, new=PJ00222 → stays as-is (already correct)
                ' The GA copy already exists in sTargetFolder, so we just need the map entry to be absent
                ' or pointing to itself (same-path guard in replace loop handles it safely).
                ' We deliberately do NOT try to rename the GA again — it's already done.
                ' Leave sTopAsmNewBase = sTopAsmOldBase so the "name didn't change" branch fires below.
                ' That skips adding the GA to oCdMap which is correct — nothing to copy.
            ElseIf String.Compare(sTopOldPrefix, sReplace, True) <> 0 Then
                sTopAsmNewBase = sReplace & sTopAsmOldBase.Substring(iFirstDash)
            End If
        End If
        ' 2) Segment replacements (same order as BuildCopyDesignRenameMap)
        For iTPSeg = 0 To oChoice.oSegFinds.Count - 1
            sSFTP = oChoice.oSegFinds.Item(iTPSeg)
            sSRTP = ""
            If oChoice.oSegReplaces IsNot Nothing AndAlso iTPSeg < oChoice.oSegReplaces.Count Then
                sSRTP = oChoice.oSegReplaces.Item(iTPSeg)
            End If
            If Trim(sSFTP) <> "" AndAlso sTopAsmNewBase.ToUpper().Contains(sSFTP.ToUpper()) Then
                sTopAsmNewBase = Trim(ReplaceAllCaseInsensitive(sTopAsmNewBase, sSFTP, sSRTP)).Replace("_ ", "_").Replace("  ", " ")
                Do While sTopAsmNewBase.Contains("__")
                    sTopAsmNewBase = sTopAsmNewBase.Replace("__", "_")
                Loop
                sTopAsmNewBase = sTopAsmNewBase.Trim("_"c).Trim()
            End If
        Next
        ' 3) Add to map if name actually changed.
        '    Full Sweep exception: when sPresetOldPrefix is set the GA is already renamed
        '    (old prefix gone from filename), so old=new is CORRECT — skip silently, don't abort.
        If String.Compare(sTopAsmNewBase, sTopAsmOldBase, True) <> 0 AndAlso sTopAsmNewBase <> "" Then
            sTopAsmNewFull = System.IO.Path.Combine(sTargetFolder, sTopAsmNewBase & sTopAsmExt)
            If Not oCdMap.ContainsKey(sTopAssemblyFullName) Then
                oCdMap(sTopAssemblyFullName) = sTopAsmNewFull
                oLog.Append(vbCrLf & "  TOP ASM MAP: " & sTopAsmOldBase & sTopAsmExt & "  ->  " & sTopAsmNewBase & sTopAsmExt)
                Try : System.IO.File.AppendAllText(sLogFilePath, "TOP ASM MAP: " & sTopAsmOldBase & sTopAsmExt & "  ->  " & sTopAsmNewBase & sTopAsmExt & vbCrLf) : Catch : End Try
            End If
        ElseIf String.Compare(sTopAsmNewBase, sTopAsmOldBase, True) = 0 OrElse sTopAsmNewBase = "" Then
            ' GA is already correctly named (old prefix not found in filename, or
            ' new name equals old name). This happens in Full Sweep AND when running
            ' the rule directly from an already-renamed assembly.
            ' Phase 2 will skip the copy (file already exists at destination).
            ' Phase 3 must still fix the GA's internal refs — add a self-ref entry.
            If Not oCdMap.ContainsKey(sTopAssemblyFullName) Then
                oCdMap(sTopAssemblyFullName) = sTopAssemblyFullName
                Try : System.IO.File.AppendAllText(sLogFilePath, "GA already correctly named — added self-ref for Phase 3 internal-ref fix: " & sTopAsmOldBase & sTopAsmExt & vbCrLf) : Catch : End Try
            End If
        Else
            ' Could not compute a renamed path — abort to avoid corrupting originals
            MessageBox.Show("Could not compute a new name for the top assembly:" & vbCrLf & sTopAsmOldBase & vbCrLf & vbCrLf & "Check that the old prefix token matches the GA filename and try again.", "Copy Design - Aborted")
            ThisApplication.SilentOperation = bOrigSilent
            Exit Sub
        End If

        GetSetPrebuiltMode2Map(True, oCdMap)
        ' Drive the Mode 2 multi-phase path with the pre-built map
        bUseContainsMode = True
        oChoice.bUseContainsMode = True
        sFind = sReplace  ' placeholder; Phase 1 uses pre-built map
        Try
            Dim sFolderMode As String = If(oChoice.bHonourFolderStructure, "HONOUR EXISTING (keep sub-folders)", "CLEAN SINGLE FOLDER (flat)")
            Dim sbHdr As New System.Text.StringBuilder()
            sbHdr.AppendLine("Mode 6 COPY DESIGN   NewPrefix='" & sReplace & "'   OldPrefixes: " & String.Join(", ", oChoice.oBatchFinds))
            sbHdr.AppendLine("  FolderMode : " & sFolderMode)
            sbHdr.AppendLine("  NonStd     : " & oChoice.bLocalizeNonStd.ToString())
            sbHdr.AppendLine("  Segments   : " & oChoice.oSegFinds.Count.ToString())
            For i As Integer = 0 To oChoice.oSegFinds.Count - 1
                sbHdr.AppendLine("    Row " & (i + 1).ToString() & "  Find='" & oChoice.oSegFinds(i) & "'  Replace='" & oChoice.oSegReplaces(i) & "'")
            Next
            sbHdr.AppendLine()
            System.IO.File.AppendAllText(sLogFilePath, sbHdr.ToString())
        Catch
        End Try
        oLog.Append(vbCrLf & "=== Mode 6 COPY DESIGN (Vault-style one-pass) ===")
        ' Fall through to Mode 2 multi-phase (bUseContainsMode = True)
        GoTo SkipBatchMode
    End If

    ' ---------- MODE 4: Batch P-prefix scan and swap ----------
    ' If the user chose Mode 4, scan the tree now to collect all P-prefixed
    ' project tokens, show a selection form, then run ProcessLevel once per
    ' selected token before falling through to the post-traversal passes.
    If oChoice.bBatchMode Then

        ' Scan
        Dim oTokenList As System.Collections.Generic.List(Of String)
        Try
            oTokenList = ScanPrefixes(oAsmDoc)
        Catch ex As Exception
            MessageBox.Show("Batch prefix scan failed: " & ex.Message & vbCrLf & "Falling back to manual Mode 1.", "Mode 4 Scan Error")
            oChoice.bBatchMode = False
            GoTo SkipBatchMode
        End Try

        ' Show selection form
        If Not ShowBatchSelectionForm(oTokenList, oChoice) Then
            MessageBox.Show("Cancelled - no changes made.", "Cancelled")
            ThisApplication.SilentOperation = bOrigSilent
            Exit Sub
        End If

        sReplace = oChoice.sReplace  ' new project number entered in the batch form
        bUseContainsMode = False     ' Mode 4 always uses STARTS WITH (Mode 1 logic)

        ' Confirm: warn if replace starts with any of the selected finds
        Dim sBatchRisk As String = ""
        For Each sBF As String In oChoice.oBatchFinds
            If sReplace.ToUpper().StartsWith(sBF.ToUpper()) AndAlso _
               String.Compare(sBF, sReplace, True) <> 0 Then
                sBatchRisk = sBF
                Exit For
            End If
        Next
        If sBatchRisk <> "" Then
            Dim oBatchSelfMatch As DialogResult = MessageBox.Show( _
                "WARNING: the new project number '" & sReplace & "' starts with" & vbCrLf & _
                "'" & sBatchRisk & "', which is one of the prefixes being replaced." & vbCrLf & vbCrLf & _
                "Running the rule again could compound the rename indefinitely." & vbCrLf & _
                "Click Yes to continue anyway, or No to cancel.", _
                "Batch Mode - Self-Match Risk", MessageBoxButtons.YesNo, MessageBoxIcon.Warning)
            If oBatchSelfMatch <> DialogResult.Yes Then
                MessageBox.Show("Cancelled - no changes made.", "Cancelled")
                ThisApplication.SilentOperation = bOrigSilent
                Exit Sub
            End If
        End If

        Try
            System.IO.File.AppendAllText(sLogFilePath, "Mode 4 (batch P-prefix swap)   Replace: '" & sReplace & "'   Prefixes: " & String.Join(", ", oChoice.oBatchFinds) & vbCrLf & vbCrLf)
        Catch
        End Try

        ' Drop any selected prefix identical to the new project number.
        Dim oEffectiveBatchFinds As New System.Collections.Generic.List(Of String)
        For Each sBF As String In oChoice.oBatchFinds
            If String.Compare(sBF, sReplace, True) <> 0 Then
                oEffectiveBatchFinds.Add(sBF)
            Else
                oLog.Append(vbCrLf & "Mode 4: skipped prefix identical to new project number: " & sBF)
            End If
        Next
        If oEffectiveBatchFinds.Count = 0 Then
            ' All found prefixes are identical to the new project number.
            ' The main rename traversal has nothing to do, but the fix-internal-refs
            ' pass may still have work (xlsx param table links, derive sources that
            ' weren't caught by previous runs). Ask the user for the old prefix.
            Dim sOldPrefixForFix As String = InputBox( _
                "All P-prefixed files in the tree are already named '" & sReplace & "'." & vbCrLf & _
                "No files need renaming." & vbCrLf & vbCrLf & _
                "However, some internal references (xlsx param tables, derive sources)" & vbCrLf & _
                "may still point to old project files. Enter the OLD prefix to search" & vbCrLf & _
                "for in internal references (e.g. PJ174, PJ00174), or leave blank to skip.", _
                "Fix Internal References Only", "")
            sOldPrefixForFix = Trim(sOldPrefixForFix)
            If sOldPrefixForFix = "" Then
                MessageBox.Show("Nothing to do - cancelled.", "Mode 4 - Nothing To Do")
                ThisApplication.SilentOperation = bOrigSilent
                Exit Sub
            End If
            ' Set sFind to the user-supplied old prefix and jump straight to
            ' the post-traversal passes - no rename traversal needed.
            sFind = sOldPrefixForFix
            oLog.Append(vbCrLf & "Mode 4: all files already renamed to '" & sReplace & "'. Running fix-internal-refs pass only with Find='" & sFind & "'.")
            If oChoice.oBatchFinds.Count > 0 Then oChoice.oBatchFinds(0) = sFind
            GoTo AfterSingleTraversal
        End If
        oChoice.oBatchFinds = oEffectiveBatchFinds

        ' Run Mode 1 logic for each selected prefix in sequence.
        ' oRenameMap is shared - a file renamed in pass 1 won't be touched again.
        ' oProcessedResults is CLEARED between passes so the performance cache
        ' doesn't prevent exploration under a different prefix.
        For Each sBatchFind As String In oChoice.oBatchFinds
            Try
                System.IO.File.AppendAllText(sLogFilePath, vbCrLf & "--- Batch pass: Find='" & sBatchFind & "'  Replace='" & sReplace & "' ---" & vbCrLf)
            Catch
            End Try
            oLog.Append(vbCrLf & "=== Batch pass: '" & sBatchFind & "'  -->  '" & sReplace & "' ===")
            oProcessedResults.Clear()  ' clear cache so each prefix gets a fresh traversal
            oVisitedLevels.Clear()
            oPathStack.Clear()
            Try
                Call ProcessLevel(oAsmDef, sBatchFind, sReplace, False, sTargetFolder, sTopAssemblyFullName, oLog, iCount, oRenameMap, oSavedInPlace, oVisitedLevels, oPathStack, oProcessedResults, sLogFilePath, , oNeedsCheckout, oChoice.oBatchFinds, sReplace)
            Catch ex As Exception
                oLog.Append(vbCrLf & "FAILED during batch pass '" & sBatchFind & "': " & ex.Message)
                Try
                    System.IO.File.AppendAllText(sLogFilePath, "FAILED during batch pass '" & sBatchFind & "': " & ex.Message & vbCrLf & ex.StackTrace)
                Catch
                End Try
            End Try
        Next

        ' Set sFind to the first selected token so PJ-number sync and derived/param
        ' passes have a valid Find value (they use sFind for their own logic).
        ' The derived/param pass loops AllReferencedDocuments anyway so covering
        ' all prefixes regardless of which sFind we use here.
        If oChoice.oBatchFinds.Count > 0 Then sFind = oChoice.oBatchFinds(0)

        ' Skip the normal single-prefix traversal below
        GoTo AfterSingleTraversal
    End If
SkipBatchMode:

    ' ---------- Guard against a self-matching Find/Replace pair (Modes 1/2/3 only) ----------
    ' Mode 4 handles its own self-match check inside the batch block above.
    ' Mode 1 (prefix swap): if REPLACE starts with FIND (e.g. Find
    ' "PJ00195", Replace "PJ00195-3610"), every renamed file's new name
    ' ALSO starts with the find text - re-running the rule (even by
    ' accident) matches its own previous output and prepends another
    ' copy indefinitely (e.g. "PJ00195-3610-3610-3610-...").
    ' Mode 2 (segment replace): if REPLACE contains FIND anywhere (e.g.
    ' Find "10", Replace "1010"), a re-run could still find and re-swap
    ' part of its own output the same way.
    ' EXCEPTION: Find and Replace being IDENTICAL is a deliberate,
    ' different, and completely safe use case - see LOCALIZE WITHOUT
    ' RENAMING in the header comment. The file name never changes, so
    ' there's nothing to compound on a re-run - it can only ever settle
    ' into "already exists here, repoint only."
    If Not oChoice.bBatchMode Then  ' Mode 4 has its own self-match guard above
    Dim bIdenticalFindReplace As Boolean = (String.Compare(sFind, sReplace, True) = 0)
    Dim bSelfMatchRisk As Boolean
    If oChoice.bConsolidateOnlyMode Then
        bSelfMatchRisk = False ' Mode 3 never renames - nothing to compound on a re-run
    ElseIf bIdenticalFindReplace Then
        bSelfMatchRisk = False
    ElseIf bUseContainsMode Then
        bSelfMatchRisk = sReplace.ToUpper().Contains(sFind.ToUpper())
    Else
        bSelfMatchRisk = sReplace.ToUpper().StartsWith(sFind.ToUpper())
    End If

    If bSelfMatchRisk Then
        Dim oSelfMatchConfirm As DialogResult = MessageBox.Show( _
            "The REPLACE text ('" & sReplace & "') " & IIf(bUseContainsMode, "contains", "starts with") & vbCrLf & _
            "the FIND text ('" & sFind & "')." & vbCrLf & vbCrLf & _
            "This means a file this rule renames could STILL match the find" & vbCrLf & _
            "text afterward - running the rule again (even by accident, e.g." & vbCrLf & _
            "re-clicking while a slow run is still going) could keep" & vbCrLf & _
            "compounding the same change indefinitely." & vbCrLf & vbCrLf & _
            "Click Yes ONLY if you're certain this is correct. Click No to" & vbCrLf & _
            "cancel and re-enter it.", _
            "Check This Before Continuing - Possible Runaway Rename", MessageBoxButtons.YesNo, MessageBoxIcon.Warning)

        If oSelfMatchConfirm <> DialogResult.Yes Then
            MessageBox.Show("Cancelled - no changes made.", "Cancelled")
            Exit Sub
        End If
    End If
    End If  ' Not bBatchMode


    Try
        System.IO.File.AppendAllText(sLogFilePath, "Mode: " & IIf(oChoice.bConsolidateOnlyMode, "3 (consolidate only)", IIf(bUseContainsMode, "2 (segment replace)", "1 (prefix swap)")) & "   Find: '" & sFind & "'" & IIf(oChoice.bConsolidateOnlyMode, "", "   Replace: '" & sReplace & "'") & vbCrLf & vbCrLf)
    Catch
    End Try

    Try
        If oChoice.bConsolidateOnlyMode Then

            ' SAFETY CHECK: warn if any document currently open in this
            ' Inventor session lives in the same original source folder as
            ' the files we're about to consolidate (i.e. the parent of
            ' sTargetFolder). If so, SaveAs will fail with E_FAIL (file
            ' locked) on any file that's open. The fix is to close Inventor
            ' completely, reopen it fresh, and open ONLY the test assembly
            ' before running Mode 3. We still proceed after the warning -
            ' the pre-SaveAs check below handles individual locked files
            ' gracefully - but this gives early visibility.
            Try
                Dim sOriginalFolder As String = System.IO.Path.GetDirectoryName(sTargetFolder.TrimEnd(System.IO.Path.DirectorySeparatorChar))
                Dim iOpenInOriginal As Integer = 0
                For Each oOpenDoc As Document In ThisApplication.Documents
                    Try
                        Dim sDocPath As String = oOpenDoc.FullFileName
                        If sDocPath.ToUpper().StartsWith(sOriginalFolder.ToUpper() & System.IO.Path.DirectorySeparatorChar) Then
                            If Not sDocPath.ToUpper().StartsWith(sTargetFolder.ToUpper() & System.IO.Path.DirectorySeparatorChar) Then
                                iOpenInOriginal = iOpenInOriginal + 1
                            End If
                        End If
                    Catch
                    End Try
                Next
                If iOpenInOriginal > 0 Then
                    MessageBox.Show( _
                        "WARNING: " & iOpenInOriginal & " file(s) from the ORIGINAL folder are currently open in this Inventor session." & vbCrLf & vbCrLf & _
                        "This can cause SaveAs to fail (E_FAIL - file locked) when Mode 3 tries to copy them." & vbCrLf & vbCrLf & _
                        "For best results: close Inventor completely, reopen it, open ONLY the test assembly, then run Mode 3 again." & vbCrLf & vbCrLf & _
                        "Proceeding anyway - locked files will be skipped and noted in the log. You can re-run Mode 3 after a fresh session to pick them up.", _
                        "Mode 3 - Session Warning", MessageBoxButtons.OK, MessageBoxIcon.Warning)
                End If
            Catch
            End Try

            ' ---------- PRE-SCAN: walk the full tree and report status of every file ----------
            ' Runs BEFORE the actual consolidation. Writes a full tree report to a
            ' separate "_PreScan.txt" file alongside the decisions log, showing every
            ' distinct file found and why it will or won't be consolidated. This is
            ' purely a read-only walk - nothing is copied, renamed, or repointed here.
            Dim sPreScanPath As String = System.IO.Path.Combine(System.IO.Path.GetDirectoryName(sLogFilePath), System.IO.Path.GetFileNameWithoutExtension(sLogFilePath) & "_PreScan.txt")
            Dim iPreScanTotal As Integer = 0
            Dim iPreScanNeedsCopy As Integer = 0
            Dim iPreScanAlreadyLocal As Integer = 0
            Dim iPreScanExcluded As Integer = 0
            Dim iPreScanSuppressed As Integer = 0
            Dim iPreScanNoPrefix As Integer = 0
            Dim iPreScanVirtual As Integer = 0
            Try
                System.IO.File.WriteAllText(sPreScanPath, "MODE 3 PRE-SCAN - " & DateTime.Now.ToString() & vbCrLf)
                System.IO.File.AppendAllText(sPreScanPath, "Top assembly: " & sTopAssemblyFullName & vbCrLf)
                System.IO.File.AppendAllText(sPreScanPath, "Target folder: " & sTargetFolder & vbCrLf)
                System.IO.File.AppendAllText(sPreScanPath, "Original source root (for subfolder mirroring): auto-detected during scan" & vbCrLf)
                System.IO.File.AppendAllText(sPreScanPath, "Find prefix: " & sFind & vbCrLf)
                System.IO.File.AppendAllText(sPreScanPath, vbCrLf & "STATUS KEY:" & vbCrLf)
                System.IO.File.AppendAllText(sPreScanPath, "  [NEEDS COPY]   - matches prefix, outside target folder -> will be consolidated" & vbCrLf)
                System.IO.File.AppendAllText(sPreScanPath, "  [ALREADY LOCAL] - matches prefix, already in correct folder -> left alone" & vbCrLf)
                System.IO.File.AppendAllText(sPreScanPath, "  [NO PREFIX]    - doesn't start with Find text -> not a consolidation target" & vbCrLf)
                System.IO.File.AppendAllText(sPreScanPath, "  [EXCLUDED]     - inside Vault Library / Content Center / Jameson Standard -> always skipped" & vbCrLf)
                System.IO.File.AppendAllText(sPreScanPath, "  [SUPPRESSED]   - suppressed occurrence -> skipped (definition not loaded)" & vbCrLf)
                System.IO.File.AppendAllText(sPreScanPath, "  [VIRTUAL]      - virtual/embedded component, no independent file -> skipped" & vbCrLf)
                System.IO.File.AppendAllText(sPreScanPath, vbCrLf & New String("-"c, 100) & vbCrLf & vbCrLf)
                Dim oPreScanVisited As New System.Collections.Generic.HashSet(Of String)
                PreScanLevel(oAsmDef, sFind, sTargetFolder, sPreScanPath, 0, oPreScanVisited, iPreScanTotal, iPreScanNeedsCopy, iPreScanAlreadyLocal, iPreScanExcluded, iPreScanSuppressed, iPreScanNoPrefix, iPreScanVirtual)
                System.IO.File.AppendAllText(sPreScanPath, vbCrLf & New String("-"c, 100) & vbCrLf)
                System.IO.File.AppendAllText(sPreScanPath, "SUMMARY:" & vbCrLf)
                System.IO.File.AppendAllText(sPreScanPath, "  Total distinct files seen:  " & iPreScanTotal & vbCrLf)
                System.IO.File.AppendAllText(sPreScanPath, "  NEEDS COPY (will consolidate): " & iPreScanNeedsCopy & vbCrLf)
                System.IO.File.AppendAllText(sPreScanPath, "  Already local:               " & iPreScanAlreadyLocal & vbCrLf)
                System.IO.File.AppendAllText(sPreScanPath, "  No matching prefix:          " & iPreScanNoPrefix & vbCrLf)
                System.IO.File.AppendAllText(sPreScanPath, "  Excluded (library/CC/std):   " & iPreScanExcluded & vbCrLf)
                System.IO.File.AppendAllText(sPreScanPath, "  Suppressed occurrences:      " & iPreScanSuppressed & vbCrLf)
                System.IO.File.AppendAllText(sPreScanPath, "  Virtual components:          " & iPreScanVirtual & vbCrLf)
            Catch ex As Exception
                oLog.Append(vbCrLf & "Pre-scan log write failed: " & ex.Message)
            End Try

            MessageBox.Show( _
                "Pre-scan complete. " & iPreScanNeedsCopy & " file(s) will be consolidated." & vbCrLf & _
                iPreScanAlreadyLocal & " already in the correct folder." & vbCrLf & _
                iPreScanNoPrefix & " don't match the prefix (not touched)." & vbCrLf & _
                iPreScanExcluded & " excluded (library/Content Center/standard)." & vbCrLf & _
                iPreScanSuppressed & " suppressed occurrence(s) found (now included - consolidated same as active)." & vbCrLf & vbCrLf & _
                "Full tree detail written to:" & vbCrLf & sPreScanPath & vbCrLf & vbCrLf & _
                "Click OK to proceed with the consolidation, or close Inventor" & vbCrLf & _
                "to abort (there is no Cancel here - the pre-scan is already done).", _
                "Mode 3 Pre-Scan Complete")

            Dim oProcessedDerivedDocs As New System.Collections.Generic.HashSet(Of String)
            Call ConsolidateLevel(oAsmDef, sFind, sTargetFolder, sTopAssemblyFullName, oLog, iCount, oRenameMap, oVisitedLevels, oPathStack, sLogFilePath, oProcessedDerivedDocs)
            ' Also check the top assembly's own linked parameter tables -
            ' these aren't reached by ConsolidateLevel since the top assembly
            ' isn't anyone's occurrence. Same pattern as the dedicated derived
            ' rule (Traverse_Through_Subs_Parts_Update_Derived_Part).
            Try
                If ConsolidateLinkedParams(oAsmDoc, sTargetFolder, oLog, iCount) Then
                    oLog.Append(vbCrLf & "Top assembly's own parameter links consolidated.")
                End If
            Catch ex As Exception
                oLog.Append(vbCrLf & "FAILED checking param links in top assembly: " & ex.Message)
            End Try
        Else
            If bUseContainsMode Then
                ' ============================================================
                ' MODE 2 - VAULT-STYLE MULTI-PHASE SEGMENT REPLACE
                ' ============================================================
                ' Problem with the old approach: it copied a file, tried to
                ' repoint parents, then DELETED the old file - but never
                ' rewrote the INTERNAL references inside newly-copied
                ' assemblies to point at their newly-renamed children. That
                ' left parents pointing at deleted (or still-old) children
                ' and forced re-runs to "catch misses".
                '
                ' Vault Copy Design solves this by:
                '   1. Building a complete old->new map first (no disk writes)
                '   2. Copying EVERY mapped file to its new name (olds kept)
                '   3. Opening each NEW assembly and rewriting its internal
                '      file references (ReferencedFileDescriptors) so they
                '      point at the other NEW files in the map
                '   4. Only then repointing live session occurrences
                '   5. Saving everything; olds are left on disk (safe; Mode 1
                '      does the same). Optionally deleted only after a clean
                '      verify pass.
                '
                ' This is the same strategy, applied to segment replace.
                ' ============================================================

                ' --- PHASE 1: BUILD COMPLETE RENAME MAP ---
                oLog.Append(vbCrLf & "Mode 2 Phase 1: building rename map...")
                Try : System.IO.File.AppendAllText(sLogFilePath, vbCrLf & "Mode 2 Phase 1: building rename map..." & vbCrLf) : Catch : End Try

                Dim oMode2Map As New System.Collections.Generic.Dictionary(Of String, String)(StringComparer.OrdinalIgnoreCase)
                ' Mode 6 Copy Design injects a pre-built master map (prefix + segments + non-std)
                Dim oPrebuilt As System.Collections.Generic.Dictionary(Of String, String) = GetSetPrebuiltMode2Map()
                Dim iMapBuilt As Integer = 0
                Dim iMapSkipped As Integer = 0
                If oPrebuilt IsNot Nothing AndAlso oPrebuilt.Count > 0 Then
                    For Each kvpPre As System.Collections.Generic.KeyValuePair(Of String, String) In oPrebuilt
                        If Not oMode2Map.ContainsKey(kvpPre.Key) Then
                            oMode2Map(kvpPre.Key) = kvpPre.Value
                            iMapBuilt = iMapBuilt + 1
                        End If
                    Next
                    oLog.Append(vbCrLf & "  Map: " & iMapBuilt & " rename(s), 0 skipped [Copy Design pre-built].")
                    Try : System.IO.File.AppendAllText(sLogFilePath, "  Map: " & iMapBuilt & " rename(s), 0 skipped. [Copy Design pre-built]" & vbCrLf) : Catch : End Try
                    GetSetPrebuiltMode2Map(True, Nothing)  ' clear after consume

                    ' SUPPLEMENTARY SCAN: the pre-built map only covers the primary old prefix
                    ' (e.g. PJ00193). Cross-project subs with OTHER old prefixes (PJ00180, PJ00190
                    ' etc.) are never in the Vault Copy Design map. Scan AllReferencedDocuments
                    ' for any file whose leading PJ-prefix is in oBatchFinds but NOT yet in oMode2Map,
                    ' and add a rename entry so they get copied and repointed too.
                    Try
                        Dim oSupplDocs As New System.Collections.Generic.List(Of Document)
                        Try
                            For Each oSD As Document In oAsmDoc.AllReferencedDocuments
                                oSupplDocs.Add(oSD)
                            Next
                        Catch : End Try
                        Dim iSuppl As Integer = 0
                        For Each oSD As Document In oSupplDocs
                            Dim sSDFull As String = ""
                            Try : sSDFull = oSD.FullFileName : Catch : Continue For : End Try
                            If oMode2Map.ContainsKey(sSDFull) Then Continue For
                            If IsInExcludedFolder(sSDFull) OrElse IsContentCenterMember(oSD) Then Continue For
                            Dim sSDBase As String = System.IO.Path.GetFileNameWithoutExtension(sSDFull)
                            Dim iSDDash As Integer = sSDBase.IndexOf("-"c)
                            If iSDDash < 2 Then Continue For
                            Dim sSDPfx As String = sSDBase.Substring(0, iSDDash)
                            ' Must be an old PJ-prefix we're targeting
                            Dim bIsTargetPfx As Boolean = False
                            For Each sBF As String In oChoice.oBatchFinds
                                If String.Compare(sSDPfx, sBF, True) = 0 Then bIsTargetPfx = True : Exit For
                            Next
                            If Not bIsTargetPfx Then Continue For
                            ' Build new name: replace old prefix with new prefix
                            Dim sSDNewBase As String = sReplace & sSDBase.Substring(iSDDash)
                            Dim sSDExt As String = System.IO.Path.GetExtension(sSDFull)
                            Dim sSDNewFull As String = System.IO.Path.Combine(sTargetFolder, sSDNewBase & sSDExt)
                            If String.Compare(sSDFull, sSDNewFull, True) = 0 Then Continue For
                            oMode2Map(sSDFull) = sSDNewFull
                            iSuppl = iSuppl + 1
                            Try : System.IO.File.AppendAllText(sLogFilePath, "  SUPPL MAP: " & sSDBase & sSDExt & "  ->  " & sSDNewBase & sSDExt & vbCrLf) : Catch : End Try
                        Next
                        If iSuppl > 0 Then
                            Try : System.IO.File.AppendAllText(sLogFilePath, "  Supplementary scan added " & iSuppl & " cross-project file(s) to map." & vbCrLf) : Catch : End Try
                        End If
                    Catch exSuppl As Exception
                        Try : System.IO.File.AppendAllText(sLogFilePath, "  Supplementary scan error: " & exSuppl.Message & vbCrLf) : Catch : End Try
                    End Try

                    GoTo Mode2Phase2
                End If
                Dim oAllDocs As New System.Collections.Generic.List(Of Document)
                oAllDocs.Add(oAsmDoc)
                Try
                    For Each oRefDoc As Document In oAsmDoc.AllReferencedDocuments
                        Try : oAllDocs.Add(oRefDoc) : Catch : End Try
                    Next
                Catch exAllRef2 As Exception
                    Try : System.IO.File.AppendAllText(sLogFilePath, "WARNING: AllReferencedDocuments failed in Phase1 (" & exAllRef2.Message & ") - falling back to open Documents." & vbCrLf) : Catch : End Try
                    For Each oFbDoc2 As Document In ThisApplication.Documents
                        Try
                            If oFbDoc2 IsNot Nothing AndAlso Not oAllDocs.Contains(oFbDoc2) Then oAllDocs.Add(oFbDoc2)
                        Catch : End Try
                    Next
                End Try

                ' Also scan File.ReferencedFileDescriptors of every assembly so
                ' we catch derived sources / xlsx / fasteners that are not
                ' component occurrences (AllReferencedDocuments can miss some).
                Dim oExtraPaths As New System.Collections.Generic.HashSet(Of String)(StringComparer.OrdinalIgnoreCase)
                For Each oDoc As Document In oAllDocs
                    Try
                        If oDoc.DocumentType <> kAssemblyDocumentObject AndAlso _
                           oDoc.DocumentType <> kPartDocumentObject Then Continue For
                        For Each oFD As FileDescriptor In oDoc.File.ReferencedFileDescriptors
                            Dim sExtra As String = ""
                            Try : sExtra = oFD.FullFileName : Catch : Continue For : End Try
                            If Trim(sExtra) = "" OrElse sExtra.Contains("*") Then Continue For
                            If Not oExtraPaths.Contains(sExtra) Then oExtraPaths.Add(sExtra)
                        Next
                    Catch
                    End Try
                Next

                ' Helper local function body inlined: consider one path for the map
                Dim oCandidatePaths As New System.Collections.Generic.List(Of String)
                For Each oDoc As Document In oAllDocs
                    Try
                        Dim sP As String = oDoc.FullFileName
                        If Trim(sP) <> "" AndAlso Not sP.Contains("*") Then oCandidatePaths.Add(sP)
                    Catch
                    End Try
                Next
                For Each sExtra As String In oExtraPaths
                    oCandidatePaths.Add(sExtra)
                Next

                For Each sOldFull As String In oCandidatePaths
                    Try
                        If Trim(sOldFull) = "" OrElse sOldFull.Contains("*") Then Continue For
                        If Not IsDocSafeToMutate(sOldFull, sTargetFolder, sTopAssemblyFullName) Then Continue For
                        If String.Compare(sOldFull, sTopAssemblyFullName, True) = 0 Then Continue For
                        If IsInExcludedFolder(sOldFull) Then Continue For
                        If oMode2Map.ContainsKey(sOldFull) Then Continue For

                        Dim sOldName As String = System.IO.Path.GetFileNameWithoutExtension(sOldFull)
                        Dim sExt As String = System.IO.Path.GetExtension(sOldFull)
                        If Not sOldName.ToUpper().Contains(sFind.ToUpper()) Then Continue For

                        Dim sNewName As String = Trim(ReplaceAllCaseInsensitive(sOldName, sFind, sReplace)).Replace("_ ", "_").Replace("  ", " ")
                        ' Collapse accidental double separators left by a blank replace
                        Do While sNewName.Contains("__")
                            sNewName = sNewName.Replace("__", "_")
                        Loop
                        sNewName = sNewName.Trim("_"c).Trim()
                        If sNewName = "" OrElse String.Compare(sNewName, sOldName, True) = 0 Then Continue For

                        Dim sNewFull As String = System.IO.Path.Combine(System.IO.Path.GetDirectoryName(sOldFull), sNewName & sExt)

                        ' Collision: target already on disk and is NOT itself a source we are renaming
                        If System.IO.File.Exists(sNewFull) AndAlso Not oMode2Map.ContainsKey(sNewFull) Then
                            ' If the existing target is the intended result of a prior partial run,
                            ' still record the mapping so internal refs get fixed to it.
                            oMode2Map(sOldFull) = sNewFull
                            oLog.Append(vbCrLf & "  MAP (target exists - will repoint only): " & sOldName & sExt & " -> " & sNewName & sExt)
                            iMapBuilt = iMapBuilt + 1
                            Continue For
                        End If

                        oMode2Map(sOldFull) = sNewFull
                        iMapBuilt = iMapBuilt + 1
                    Catch
                    End Try
                Next

                oLog.Append(vbCrLf & "  Map: " & iMapBuilt & " rename(s), " & iMapSkipped & " skipped")
                Try : System.IO.File.AppendAllText(sLogFilePath, "  Map: " & iMapBuilt & " rename(s), " & iMapSkipped & " skipped." & vbCrLf) : Catch : End Try

Mode2Phase2:
                ' --- OPTIONAL VAULT CHECKOUT of files that will be modified ---
                ' Only offer when:
                '   - the files are read-only (likely already in Vault), AND
                '   - we are not creating new files (fresh Copy Design).
                ' Fresh Copy Design creates new local files — no checkout needed.
                Try
                    Dim iCheckoutCandidates As Integer = 0
                    Dim iNewFiles As Integer = 0
                    For Each kvpChk As System.Collections.Generic.KeyValuePair(Of String, String) In oMode2Map
                        If String.Compare(kvpChk.Key, kvpChk.Value, True) = 0 Then Continue For
                        If Not System.IO.File.Exists(kvpChk.Value) Then iNewFiles += 1
                        Try
                            Dim oAttr As System.IO.FileAttributes = System.IO.File.GetAttributes(kvpChk.Key)
                            If (oAttr And System.IO.FileAttributes.ReadOnly) = System.IO.FileAttributes.ReadOnly Then
                                iCheckoutCandidates += 1
                            End If
                        Catch : End Try
                    Next
                    ' Suppress the prompt on a fresh Copy Design (new files being created)
                    If iNewFiles > 0 Then iCheckoutCandidates = 0
                    If iCheckoutCandidates > 0 Then
                        Dim sChkResult As DialogResult = MessageBox.Show(
                            "About to modify " & iCheckoutCandidates & " file(s)." & vbCrLf & vbCrLf &
                            "Check them out from Vault now (recommended to avoid save failures)?" & vbCrLf &
                            "(Uses VaultCheckOutTop and auto-confirms the dialog.)",
                            "Vault Checkout",
                            MessageBoxButtons.YesNo,
                            MessageBoxIcon.Question)
                        If sChkResult = DialogResult.Yes Then
                            Try
                                ThisApplication.CommandManager.ControlDefinitions.Item("VaultCheckOutTop").Execute2(False)
                                System.Windows.Forms.SendKeys.SendWait(Chr(9) & vbCrLf)
                                oLog.Append(vbCrLf & "  Vault checkout command issued for " & iCheckoutCandidates & " candidate(s).")
                                Try : System.IO.File.AppendAllText(sLogFilePath, "Vault checkout issued." & vbCrLf) : Catch : End Try
                            Catch exChk As Exception
                                oLog.Append(vbCrLf & "  Vault checkout failed: " & exChk.Message)
                                Try : System.IO.File.AppendAllText(sLogFilePath, "Vault checkout failed: " & exChk.Message & vbCrLf) : Catch : End Try
                            End Try
                        End If
                    End If
                Catch : End Try

                If iMapBuilt > 0 Then
                    ' --- PHASE 2: COPY ALL FILES (olds kept, no repointing yet) ---
                    oLog.Append(vbCrLf & "Mode 2 Phase 2: copying " & iMapBuilt & " file(s)...")
                    Try : System.IO.File.AppendAllText(sLogFilePath, "Mode 2 Phase 2: copying files..." & vbCrLf) : Catch : End Try

                    Dim iCopied As Integer = 0
                    Dim iCopyFailed As Integer = 0
                    Dim iAlreadyThere As Integer = 0
                    For Each kvp As System.Collections.Generic.KeyValuePair(Of String, String) In oMode2Map
                        Dim sOldFull As String = kvp.Key
                        Dim sNewFull As String = kvp.Value
                        Dim sOldName As String = System.IO.Path.GetFileName(sOldFull)
                        Dim sNewName As String = System.IO.Path.GetFileName(sNewFull)
                        Try
                            ' If the target already exists and is not the same file as the source,
                            ' check whether a previous pass (e.g. Mode 6 DrawingCopyMode) already
                            ' copied this exact file there.  If the content appears identical, reuse
                            ' the existing copy — do NOT generate a _Duplicate name.  A _Duplicate
                            ' would propagate into the assembly tree as a spurious new occurrence.
                            If System.IO.File.Exists(sNewFull) AndAlso String.Compare(sOldFull, sNewFull, True) <> 0 Then
                                If FilesAppearIdentical(sOldFull, sNewFull) Then
                                    ' Already correctly placed by a prior phase — reuse it.
                                    oRenameMap(sOldFull) = sNewFull
                                    iAlreadyThere += 1
                                    Try : System.IO.File.AppendAllText(sLogFilePath, "REUSE (already placed by prior phase): " & sOldName & " -> " & sNewName & vbCrLf) : Catch : End Try
                                    Continue For
                                End If
                            End If
                            If System.IO.File.Exists(sNewFull) AndAlso String.Compare(sOldFull, sNewFull, True) <> 0 Then
                                Dim sDestDir2 As String = System.IO.Path.GetDirectoryName(sNewFull)
                                Dim sBase2 As String = System.IO.Path.GetFileNameWithoutExtension(sNewFull)
                                Dim sExt2 As String = System.IO.Path.GetExtension(sNewFull)
                                Dim oClaimed2 As New System.Collections.Generic.HashSet(Of String)(StringComparer.OrdinalIgnoreCase)
                                For Each sC As String In oMode2Map.Values
                                    oClaimed2.Add(sC)
                                Next
                                Dim sNext2 As String = NextFreeSequenceName(sDestDir2, sBase2, sExt2, oClaimed2)
                                If sNext2 <> "" Then
                                    sNewName = sNext2 & sExt2
                                    sNewFull = System.IO.Path.Combine(sDestDir2, sNewName)
                                    Try : System.IO.File.AppendAllText(sLogFilePath, "COLLISION (Phase2): " & sOldName & " -> " & sNewName & " (next free sequence)" & vbCrLf) : Catch : End Try
                                    oLog.Append(vbCrLf & "  COLLISION (Phase2 next sequence): " & sOldName & " -> " & sNewName)
                                End If
                            End If
                            If System.IO.File.Exists(sNewFull) Then
                                iAlreadyThere = iAlreadyThere + 1
                                oRenameMap(sOldFull) = sNewFull
                                Continue For
                            End If
                            If Not System.IO.File.Exists(sOldFull) Then
                                oLog.Append(vbCrLf & "  COPY SKIP (source missing): " & sOldName)
                                iCopyFailed = iCopyFailed + 1
                                Continue For
                            End If
                            ' Clear RO on source so copy inherits clean attributes where possible
                            Try
                                Dim oA As System.IO.FileAttributes = System.IO.File.GetAttributes(sOldFull)
                                If (oA And System.IO.FileAttributes.ReadOnly) = System.IO.FileAttributes.ReadOnly Then
                                    System.IO.File.SetAttributes(sOldFull, oA And Not System.IO.FileAttributes.ReadOnly)
                                End If
                            Catch : End Try

                            Dim sDestDir As String = System.IO.Path.GetDirectoryName(sNewFull)
                            If Not System.IO.Directory.Exists(sDestDir) Then System.IO.Directory.CreateDirectory(sDestDir)
                            System.IO.File.Copy(sOldFull, sNewFull, False)
                            Try
                                Dim oNA As System.IO.FileAttributes = System.IO.File.GetAttributes(sNewFull)
                                If (oNA And System.IO.FileAttributes.ReadOnly) = System.IO.FileAttributes.ReadOnly Then
                                    System.IO.File.SetAttributes(sNewFull, oNA And Not System.IO.FileAttributes.ReadOnly)
                                End If
                            Catch : End Try

                            oRenameMap(sOldFull) = sNewFull
                            iCopied = iCopied + 1
                            iCount = iCount + 1
                            oLog.Append(vbCrLf & "  COPIED: " & sOldName & "  ->  " & sNewName)
                            Try : System.IO.File.AppendAllText(sLogFilePath, sOldName & "  ->  " & sNewName & vbCrLf) : Catch : End Try
                        Catch exCopy As Exception
                            iCopyFailed = iCopyFailed + 1
                            oLog.Append(vbCrLf & "  COPY FAILED: " & sOldName & " (" & exCopy.Message & ")")
                        End Try
                    Next
                    oLog.Append(vbCrLf & "  Phase 2 done: " & iCopied & " copied, " & iAlreadyThere & " already present, " & iCopyFailed & " failed.")
                    Try : System.IO.File.AppendAllText(sLogFilePath, "Phase 2 done: " & iCopied & " copied, " & iAlreadyThere & " already present, " & iCopyFailed & " failed." & vbCrLf) : Catch : End Try

                    ' --- PHASE 3: FIX INTERNAL REFS INSIDE EVERY NEW ASSEMBLY/PART ---
                    ' This is the critical Vault-style step the old Mode 2 skipped.
                    ' For each newly-copied (or already-present) target file that is
                    ' an assembly or part, open it and rewrite any FileDescriptor
                    ' that still points at an OLD path in the map to the NEW path.
                    oLog.Append(vbCrLf & "Mode 2 Phase 3: fixing internal references in new files...")
                    Try : System.IO.File.AppendAllText(sLogFilePath, "Mode 2 Phase 3: fixing internal refs..." & vbCrLf) : Catch : End Try

                    Dim iInternalFixed As Integer = 0
                    Dim iInternalFailed As Integer = 0
                    ' Process assemblies deepest-first so nested children are
                    ' consistent before their parents are saved.
                    Dim oNewTargets As New System.Collections.Generic.List(Of String)
                    Dim oSeenNew As New System.Collections.Generic.HashSet(Of String)(StringComparer.OrdinalIgnoreCase)
                    For Each kvp As System.Collections.Generic.KeyValuePair(Of String, String) In oMode2Map
                        If Not oSeenNew.Contains(kvp.Value) Then
                            oSeenNew.Add(kvp.Value)
                            oNewTargets.Add(kvp.Value)
                        End If
                    Next
                    oNewTargets.Sort(Function(a, b2) b2.Length.CompareTo(a.Length))

                    For Each sNewFull As String In oNewTargets
                        Dim sNewName As String = System.IO.Path.GetFileName(sNewFull)
                        Dim sExtU As String = System.IO.Path.GetExtension(sNewFull).ToUpper()
                        If sExtU <> ".IAM" AndAlso sExtU <> ".IPT" Then Continue For
                        If Not System.IO.File.Exists(sNewFull) Then Continue For

                        Dim bOpenedHere As Boolean = False
                        Dim oNewDoc As Document = OpenDocTracked(sNewFull, bOpenedHere)
                        If oNewDoc Is Nothing Then
                            Dim sOpenFail As String = "  Phase3 FAIL (could not open): " & sNewName
                            oLog.Append(vbCrLf & sOpenFail)
                            Try : System.IO.File.AppendAllText(sLogFilePath, sOpenFail & vbCrLf) : Catch : End Try
                            iInternalFailed = iInternalFailed + 1
                            Continue For
                        End If

                        Dim bDocChanged As Boolean = False
                        Try
                            ' Clear RO so Save can succeed
                            Try
                                Dim oFa As System.IO.FileAttributes = System.IO.File.GetAttributes(sNewFull)
                                If (oFa And System.IO.FileAttributes.ReadOnly) = System.IO.FileAttributes.ReadOnly Then
                                    System.IO.File.SetAttributes(sNewFull, oFa And Not System.IO.FileAttributes.ReadOnly)
                                End If
                            Catch : End Try

                            ' 3a) File-level ReferencedFileDescriptors (covers parts,
                            ' fasteners, xlsx, and anything not reachable via Occurrences)
                            For Each oFD As FileDescriptor In oNewDoc.File.ReferencedFileDescriptors
                                Dim sRefFull As String = ""
                                Try : sRefFull = oFD.FullFileName : Catch : Continue For : End Try
                                If Trim(sRefFull) = "" Then Continue For
                                Dim sTargetRef As String = ""
                                If oMode2Map.ContainsKey(sRefFull) Then
                                    sTargetRef = oMode2Map(sRefFull)
                                ElseIf oRenameMap.ContainsKey(sRefFull) Then
                                    sTargetRef = oRenameMap(sRefFull)
                                End If
                                If sTargetRef = "" Then Continue For
                                If String.Compare(sTargetRef, sRefFull, True) = 0 Then Continue For
                                Try
                                    oFD.ReplaceReference(sTargetRef)
                                    bDocChanged = True
                                    iInternalFixed = iInternalFixed + 1
                                    oLog.Append(vbCrLf & "  INTERNAL FD: " & sNewName & " : " & System.IO.Path.GetFileName(sRefFull) & " -> " & System.IO.Path.GetFileName(sTargetRef))
                                Catch exFD As Exception
                                    ' E_INVALIDARG (0x80070057) is thrown by Inventor when the FD
                                    ' belongs to a Content Centre / library part whose descriptor is
                                    ' not writable via ReplaceReference.  The file still resolves
                                    ' from its original location and Phase 4 repoints the live
                                    ' occurrence, so this is a safe skip - do NOT count as failure.
                                    If exFD.HResult = &H80070057 Then
                                        Dim sFdSkip As String = "  Phase3 SKIP (FD locked/CC): " & sNewName & " : " & System.IO.Path.GetFileName(sRefFull)
                                        oLog.Append(vbCrLf & sFdSkip)
                                    Else
                                        iInternalFailed = iInternalFailed + 1
                                        Dim sFdFail As String = "  Phase3 FAIL (FD): " & sNewName & " : " & System.IO.Path.GetFileName(sRefFull) & " (" & exFD.Message & ")"
                                        oLog.Append(vbCrLf & sFdFail)
                                        Try : System.IO.File.AppendAllText(sLogFilePath, sFdFail & vbCrLf) : Catch : End Try
                                    End If
                                End Try
                            Next

                            ' 3b) Occurrence.Replace for assemblies (handles patterns /
                            '     adaptive / DA-managed cases where FD alone is not enough)
                            If oNewDoc.DocumentType = kAssemblyDocumentObject Then
                                Try
                                    Dim oNewAsmDef As AssemblyComponentDefinition = oNewDoc.ComponentDefinition
                                    Dim oOccSnapshot As New System.Collections.Generic.List(Of ComponentOccurrence)
                                    For Each oOcc As ComponentOccurrence In oNewAsmDef.Occurrences
                                        oOccSnapshot.Add(oOcc)
                                    Next
                                    For Each oOcc As ComponentOccurrence In oOccSnapshot
                                        Dim sOccFull As String = ""
                                        Try : sOccFull = oOcc.Definition.Document.FullFileName : Catch
                                            Try : sOccFull = oOcc.ReferencedFileDescriptor.FullFileName : Catch : Continue For : End Try
                                        End Try
                                        If Trim(sOccFull) = "" Then Continue For
                                        Dim sTargetOcc As String = ""
                                        If oMode2Map.ContainsKey(sOccFull) Then
                                            sTargetOcc = oMode2Map(sOccFull)
                                        ElseIf oRenameMap.ContainsKey(sOccFull) Then
                                            sTargetOcc = oRenameMap(sOccFull)
                                        End If
                                        If sTargetOcc = "" OrElse String.Compare(sTargetOcc, sOccFull, True) = 0 Then Continue For
                                        Dim bRep As Boolean = False
                                        Try
                                            oOcc.Replace(sTargetOcc, False)
                                            bRep = True
                                        Catch
                                            Try
                                                Dim oFD2 As FileDescriptor = oOcc.ReferencedFileDescriptor
                                                If oFD2 IsNot Nothing Then
                                                    oFD2.ReplaceReference(sTargetOcc)
                                                    bRep = True
                                                End If
                                            Catch : End Try
                                        End Try
                                        If bRep Then
                                            bDocChanged = True
                                            Try : oOcc.Name = System.IO.Path.GetFileNameWithoutExtension(sTargetOcc) : Catch : End Try
                                            iInternalFixed = iInternalFixed + 1
                                        End If
                                    Next
                                Catch exOcc As Exception
                                    oLog.Append(vbCrLf & "  INTERNAL OCC FAILED: " & sNewName & " (" & exOcc.Message & ")")
                                End Try
                            End If

                            If bDocChanged Then
                                Try
                                    ' NOTE: Do NOT call oNewDoc.Update() here.
                                    ' Phase 3 opens each new .iam in isolation; at this point its
                                    ' children still reference old names on disk (Phase 3 hasn't
                                    ' finished fixing them all yet). Update() asks Inventor to
                                    ' rebuild/resolve the assembly - it encounters unresolved
                                    ' references and the subsequent Save2 then fails or saves a
                                    ' degraded file. We only need to persist the rewritten
                                    ' FileDescriptors, not rebuild the model. Save2 alone does that.
                                    oNewDoc.Save2(False)
                                    oLog.Append(vbCrLf & "  INTERNAL: saved " & sNewName)
                                Catch exSave As Exception
                                    Dim sSaveFail As String = "  Phase3 FAIL (save): " & sNewName & " (" & exSave.Message & ")"
                                    oLog.Append(vbCrLf & sSaveFail)
                                    Try : System.IO.File.AppendAllText(sLogFilePath, sSaveFail & vbCrLf) : Catch : End Try
                                    iInternalFailed = iInternalFailed + 1
                                End Try
                            End If
                        Catch exDoc As Exception
                            Dim sDocFail As String = "  Phase3 FAIL (doc error): " & sNewName & " (" & exDoc.Message & ")"
                            oLog.Append(vbCrLf & sDocFail)
                            Try : System.IO.File.AppendAllText(sLogFilePath, sDocFail & vbCrLf) : Catch : End Try
                            iInternalFailed = iInternalFailed + 1
                        End Try

                        ' Close if WE opened it and it was not already in session at rule start.
                        ' Keeps memory flat during Phase 3 on large trees.
                        CloseIfOpenedHere(oNewDoc, bOpenedHere)
                        oNewDoc = Nothing
                        PeriodicGcTick()
                    Next
                    oLog.Append(vbCrLf & "  Phase 3 done: " & iInternalFixed & " internal ref(s) fixed, " & iInternalFailed & " failure(s).")
                    Try : System.IO.File.AppendAllText(sLogFilePath, "Phase 3 done: " & iInternalFixed & " fixed, " & iInternalFailed & " failed." & vbCrLf) : Catch : End Try

                    ' --- MEMORY FLUSH between Phase 3 and Phase 4 ---
                    ' Phase 3 saves and closes documents it opened itself, but sub-assemblies
                    ' that were ALREADY open at rule start (and were then dirtied by Phase 3
                    ' internal-ref fixes) are left dirty and open — the old flush skipped them
                    ' because bDirty=True. This caused 0 closes and 143 open assemblies going
                    ' into Phase 4, blowing up memory. New logic: save dirty non-top docs first,
                    ' then close everything not in the initial snapshot and not the top GA.
                    Try
                        Dim oSnap As System.Collections.Generic.HashSet(Of String) = GetSetInitiallyOpenDocs()
                        Dim oToClose As New System.Collections.Generic.List(Of Document)
                        For Each oD As Document In ThisApplication.Documents
                            Try
                                Dim sP As String = oD.FullFileName
                                If Trim(sP) = "" Then Continue For
                                If String.Compare(sP, sTopAssemblyFullName, True) = 0 Then Continue For
                                If oSnap IsNot Nothing AndAlso oSnap.Contains(sP) Then Continue For
                                ' Save if dirty and inside our target folder (never save originals)
                                Dim bDirty As Boolean = False
                                Try : bDirty = oD.Dirty : Catch : End Try
                                If bDirty AndAlso IsDocSafeToMutate(sP, sTargetFolder, sTopAssemblyFullName) Then
                                    Try : oD.Save2(False) : Catch : End Try
                                End If
                                oToClose.Add(oD)  ' close regardless of dirty flag
                            Catch
                            End Try
                        Next
                        Dim iFlushed As Integer = 0
                        For Each oD As Document In oToClose
                            Try
                                oD.Close(False)
                                iFlushed = iFlushed + 1
                            Catch
                            End Try
                        Next
                        oLog.Append(vbCrLf & "  Pre-Phase4 flush: closed " & iFlushed & " residual document(s).")
                        Try : System.IO.File.AppendAllText(sLogFilePath, "Pre-Phase4 flush: closed " & iFlushed & " residual doc(s)." & vbCrLf) : Catch : End Try
                    Catch
                    End Try

                    ' --- PHASE 4: REPOINT LIVE TREE (ALL OPEN ASSEMBLIES) ---
                    ' Walk every currently-open assembly document in the session
                    ' (not just the top). Nested sub-assemblies that still hold
                    ' occurrences pointing at old-segment files are updated here.
                    ' Prefer FileDescriptor.ReplaceReference (lightweight) then
                    ' fall back to Occurrence.Replace when needed. DA-protected
                    ' parents (bolted connections / frames) are handled via the
                    ' existing header-level path.
                    oLog.Append(vbCrLf & "Mode 2 Phase 4: repointing live occurrences in ALL open assemblies...")
                    Try : System.IO.File.AppendAllText(sLogFilePath, "Mode 2 Phase 4: repointing live occurrences (full tree)..." & vbCrLf) : Catch : End Try

                    Dim iLiveRepointed As Integer = 0
                    Dim iLiveFailed As Integer = 0
                    Dim oPhase4Failures As New System.Collections.Generic.List(Of String)

                    ' O(1) filename fallback map - ONLY true renames (old filename <> new filename).
                    ' No-op / same-name entries (e.g. non-std parts that kept their descriptive name)
                    ' are excluded so Phase 4 does not attempt useless ReplaceReference calls.
                    ' IMPORTANT: built from oRenameMap (Phase 2 actuals) NOT oMode2Map (Phase 1 plan),
                    ' so Phase 4 targets the files that were actually placed on disk — including any
                    ' that were reused from a prior pass (e.g. Mode 6 DrawingCopyMode copies).
                    Dim oNameToNew As New System.Collections.Generic.Dictionary(Of String, String)(StringComparer.OrdinalIgnoreCase)
                    For Each kvpM As System.Collections.Generic.KeyValuePair(Of String, String) In oRenameMap
                        Dim sOldFn As String = System.IO.Path.GetFileName(kvpM.Key)
                        Dim sNewFn As String = System.IO.Path.GetFileName(kvpM.Value)
                        If String.Compare(sOldFn, sNewFn, True) = 0 Then Continue For   ' same name - skip
                        If Not oNameToNew.ContainsKey(sOldFn) Then oNameToNew(sOldFn) = kvpM.Value
                    Next

                    ' Save-as-you-go: each assembly is saved immediately after its repoints.
                    ' No longer needed as a batch list — kept for top-assembly deferred save.
                    Dim oParentsToSave As New System.Collections.Generic.HashSet(Of String)(StringComparer.OrdinalIgnoreCase)
                    ' Collect every open assembly (working tree only)
                    Dim oAsmDocsToWalk As New System.Collections.Generic.List(Of Document)
                    Dim oSeenWalk As New System.Collections.Generic.HashSet(Of String)(StringComparer.OrdinalIgnoreCase)
                    Try
                        For Each oD As Document In ThisApplication.Documents
                            Try
                                If oD.DocumentType <> kAssemblyDocumentObject Then Continue For
                                Dim sP As String = oD.FullFileName
                                If Trim(sP) = "" OrElse sP.Contains("*") Then Continue For
                                If IsInExcludedFolder(sP) Then Continue For
                                If oSeenWalk.Contains(sP) Then Continue For
                                oSeenWalk.Add(sP)
                                oAsmDocsToWalk.Add(oD)
                            Catch
                            End Try
                        Next
                    Catch
                    End Try
                    If oAsmDocsToWalk.Count = 0 Then oAsmDocsToWalk.Add(oAsmDoc)
                    oLog.Append(vbCrLf & "  Phase 4 will examine " & oAsmDocsToWalk.Count & " open assembly document(s).")
                    Try : System.IO.File.AppendAllText(sLogFilePath, "  Phase 4 examining " & oAsmDocsToWalk.Count & " open assembly(s)." & vbCrLf) : Catch : End Try

                    ' --- PHASE 4 CHECKPOINT (resume support for large projects) ---
                    ' Records assemblies successfully processed so a later run can skip them.
                    Dim sPhase4CheckpointPath As String = System.IO.Path.Combine( _
                        System.IO.Path.GetDirectoryName(sLogFilePath), _
                        System.IO.Path.GetFileNameWithoutExtension(sLogFilePath) & "_Phase4Done.txt")
                    ' Also look for any previous checkpoint in the same folder (from an earlier crash)
                    Dim oPhase4AlreadyDone As New System.Collections.Generic.HashSet(Of String)(StringComparer.OrdinalIgnoreCase)
                    Try
                        Dim sChkFolder As String = System.IO.Path.GetDirectoryName(sLogFilePath)
                        For Each sPrev As String In System.IO.Directory.GetFiles(sChkFolder, "*_Phase4Done.txt")
                            For Each sLine As String In System.IO.File.ReadAllLines(sPrev)
                                Dim sTrim As String = Trim(sLine)
                                If sTrim <> "" Then oPhase4AlreadyDone.Add(sTrim)
                            Next
                        Next
                        If oPhase4AlreadyDone.Count > 0 Then
                            oLog.Append(vbCrLf & "  Phase 4: loaded " & oPhase4AlreadyDone.Count & " previously completed assembly path(s) to skip.")
                            Try : System.IO.File.AppendAllText(sLogFilePath, "Phase 4 checkpoint: skipping " & oPhase4AlreadyDone.Count & " already-done assemblies." & vbCrLf) : Catch : End Try
                        End If
                    Catch : End Try

                    ' Unique path holder for Phase 4 walk (declared once, outside loop, to avoid hide errors)
                    Dim sPhase4CurrentDocFullName As String = ""

                    For Each oWalkDoc As Document In oAsmDocsToWalk
                        Try
                            sPhase4CurrentDocFullName = ""
                            Try : sPhase4CurrentDocFullName = oWalkDoc.FullFileName : Catch : sPhase4CurrentDocFullName = "" : End Try
                            ' SAFETY: never repoint (and therefore dirty) assemblies outside sTargetFolder.
                            ' Source/original assemblies are open in the session but must never be modified.
                            If Trim(sPhase4CurrentDocFullName) = "" OrElse Not IsDocSafeToMutate(sPhase4CurrentDocFullName, sTargetFolder, sTopAssemblyFullName) Then Continue For
                            ' Skip if already completed in a previous run
                            If oPhase4AlreadyDone.Contains(sPhase4CurrentDocFullName) Then Continue For
                            Try
                                Dim oWA As System.IO.FileAttributes = System.IO.File.GetAttributes(sPhase4CurrentDocFullName)
                                If (oWA And System.IO.FileAttributes.ReadOnly) = System.IO.FileAttributes.ReadOnly Then
                                    System.IO.File.SetAttributes(sPhase4CurrentDocFullName, oWA And Not System.IO.FileAttributes.ReadOnly)
                                End If
                            Catch : End Try

                            ' File descriptors first (lightweight - no load of target)
                            Try
                                For Each oFD As FileDescriptor In oWalkDoc.File.ReferencedFileDescriptors
                                    Dim sRef As String = ""
                                    Try : sRef = oFD.FullFileName : Catch : Continue For : End Try
                                    If Trim(sRef) = "" Then Continue For
                                    Dim sNew As String = ""
                                    If oMode2Map.ContainsKey(sRef) Then
                                        sNew = oMode2Map(sRef)
                                    Else
                                        Dim sFn As String = System.IO.Path.GetFileName(sRef)
                                        If oNameToNew.ContainsKey(sFn) Then sNew = oNameToNew(sFn)
                                    End If
                                    If Trim(sNew) = "" Then Continue For
                                    If String.Compare(sRef, sNew, True) = 0 Then Continue For
                                    Try
                                        oFD.ReplaceReference(sNew)
                                        iLiveRepointed = iLiveRepointed + 1
                                        oParentsToSave.Add(sPhase4CurrentDocFullName)
                                        If (iLiveRepointed Mod 25) = 0 Then
                                            Try : System.IO.File.AppendAllText(sLogFilePath, "  Phase 4 progress: " & iLiveRepointed & " FD/occ repointed..." & vbCrLf) : Catch : End Try
                                            Try : GC.Collect() : GC.WaitForPendingFinalizers() : Catch : End Try
                                        End If
                                    Catch exFD As Exception
                                        iLiveFailed = iLiveFailed + 1
                                        Try : oPhase4Failures.Add("FD: " & System.IO.Path.GetFileName(sPhase4CurrentDocFullName) & " | " & System.IO.Path.GetFileName(sRef) & " -> " & System.IO.Path.GetFileName(sNew) & " | " & exFD.Message) : Catch : End Try
                                    End Try
                                Next
                            Catch
                            End Try

                            ' First-level occurrences only (Phase 3 fixed nested internals)
                            Try
                                Dim oWDef As AssemblyComponentDefinition = oWalkDoc.ComponentDefinition
                                Dim oOccSnap As New System.Collections.Generic.List(Of ComponentOccurrence)
                                For Each oOcc As ComponentOccurrence In oWDef.Occurrences
                                    oOccSnap.Add(oOcc)
                                Next
                                For Each oOcc As ComponentOccurrence In oOccSnap
                                    Dim sOccFull As String = ""
                                    Try
                                        sOccFull = oOcc.ReferencedFileDescriptor.FullFileName
                                    Catch
                                        Try : sOccFull = oOcc.Definition.Document.FullFileName : Catch : Continue For : End Try
                                    End Try
                                    If Trim(sOccFull) = "" Then Continue For
                                    Dim sNew As String = ""
                                    If oMode2Map.ContainsKey(sOccFull) Then
                                        sNew = oMode2Map(sOccFull)
                                    Else
                                        Dim sOccName As String = System.IO.Path.GetFileName(sOccFull)
                                        If oNameToNew.ContainsKey(sOccName) Then sNew = oNameToNew(sOccName)
                                    End If
                                    If Trim(sNew) = "" Then Continue For
                                    If String.Compare(sOccFull, sNew, True) = 0 Then Continue For
                                    ' --- Suppressed occurrence handling ---
                                    ' Suppressed occurrences are not loaded in session; ReplaceReference fails
                                    ' on their FileDescriptor unless we unsuppress first.
                                    Dim bWasSuppressed As Boolean = False
                                    Try
                                        If oOcc.Suppressed Then
                                            bWasSuppressed = True
                                            oOcc.SuppressedStatus = kNotSuppressed
                                            Try : System.IO.File.AppendAllText(sLogFilePath, "  Phase 4 UNSUPPRESS (temp): " & System.IO.Path.GetFileName(sOccFull) & vbCrLf) : Catch : End Try
                                        End If
                                    Catch : End Try
                                    ' Prefer ReplaceReference (does not force-load target)
                                    Dim bRep As Boolean = False
                                    Try
                                        Dim oFD2 As FileDescriptor = oOcc.ReferencedFileDescriptor
                                        If oFD2 IsNot Nothing Then
                                            oFD2.ReplaceReference(sNew)
                                            bRep = True
                                        End If
                                    Catch : End Try
                                    If Not bRep Then
                                        Try : oOcc.Replace(sNew, False) : bRep = True : Catch : End Try
                                    End If
                                    If bRep Then
                                        iLiveRepointed = iLiveRepointed + 1
                                        oParentsToSave.Add(sPhase4CurrentDocFullName)
                                        ' Rename browser node BEFORE re-suppressing —
                                        ' Inventor ignores Name writes on suppressed occs
                                        Try : oOcc.Name = System.IO.Path.GetFileNameWithoutExtension(sNew) : Catch : End Try
                                    End If
                                    ' Re-suppress if we temporarily unsuppressed it
                                    If bWasSuppressed Then
                                        Try
                                            oOcc.SuppressedStatus = kFullySuppressed
                                            Try : System.IO.File.AppendAllText(sLogFilePath, "  Phase 4 RE-SUPPRESS: " & System.IO.Path.GetFileName(sNew) & vbCrLf) : Catch : End Try
                                        Catch : End Try
                                    End If
                                    If bRep Then
                                        If (iLiveRepointed Mod 25) = 0 Then
                                            Try : System.IO.File.AppendAllText(sLogFilePath, "  Phase 4 progress: " & iLiveRepointed & " FD/occ repointed..." & vbCrLf) : Catch : End Try
                                            Try : GC.Collect() : GC.WaitForPendingFinalizers() : Catch : End Try
                                        End If
                                    Else
                                        ' Bolted Connection / fastener fallback.
                                        ' DA-protected assemblies block occurrence Replace; try FileDescriptor path.
                                        Dim sOccNameU As String = System.IO.Path.GetFileName(sOccFull).ToUpper()
                                        Dim bLooksFastener As Boolean = _
                                            sOccNameU.Contains("AS 1110") OrElse sOccNameU.Contains("AS 1112") OrElse _
                                            sOccNameU.Contains("AS 1252") OrElse sOccNameU.Contains("AS 1237") OrElse _
                                            sOccNameU.Contains("DIN ") OrElse sOccNameU.Contains("ISO ") OrElse _
                                            sOccNameU.Contains("NYLOCK") OrElse sOccNameU.Contains("WASHER")
                                        Dim bBcFixed As Boolean = False
                                        If bLooksFastener Then
                                            Try
                                                For Each oBcFD As FileDescriptor In oWalkDoc.File.ReferencedFileDescriptors
                                                    Dim sBcRef As String = ""
                                                    Try : sBcRef = oBcFD.FullFileName : Catch : Continue For : End Try
                                                    If String.Compare(sBcRef, sOccFull, True) = 0 Then
                                                        oBcFD.ReplaceReference(sNew)
                                                        bBcFixed = True
                                                        Exit For
                                                    End If
                                                Next
                                            Catch : End Try
                                        End If
                                        If bBcFixed Then
                                            iLiveRepointed = iLiveRepointed + 1
                                            oParentsToSave.Add(sPhase4CurrentDocFullName)
                                            Try : System.IO.File.AppendAllText(sLogFilePath, "  Phase 4 BC-FALLBACK OK: " & System.IO.Path.GetFileName(sOccFull) & " -> " & System.IO.Path.GetFileName(sNew) & vbCrLf) : Catch : End Try
                                        Else
                                            iLiveFailed = iLiveFailed + 1
                                            Try : oPhase4Failures.Add("OCC: " & System.IO.Path.GetFileName(sPhase4CurrentDocFullName) & " | " & System.IO.Path.GetFileName(sOccFull) & " -> " & System.IO.Path.GetFileName(sNew) & " | ReplaceReference/Replace failed") : Catch : End Try
                                            If bWasSuppressed Then
                                                Try : System.IO.File.AppendAllText(sLogFilePath, "  Phase 4 SUPPRESSED REPOINT FAILED: " & System.IO.Path.GetFileName(sOccFull) & vbCrLf) : Catch : End Try
                                            End If
                                        End If
                                    End If
                                Next
                            Catch
                            End Try
                        Catch
                        End Try

                        ' SAVE-AS-YOU-GO: immediately save this assembly if changed (not top).
                        ' Saves memory by letting Inventor flush dirty COM state after each asm.
                        ' The top assembly is saved later after Phase 4b verification.
                        If oParentsToSave.Contains(sPhase4CurrentDocFullName) Then
                            If String.Compare(sPhase4CurrentDocFullName, sTopAssemblyFullName, True) <> 0 Then
                                If IsDocSafeToMutate(sPhase4CurrentDocFullName, sTargetFolder, sTopAssemblyFullName) Then
                                    Try : oWalkDoc.Update() : Catch : End Try
                                    Try : oWalkDoc.Save2(False) : Catch : End Try
                                End If
                            End If
                        End If
                        ' Checkpoint: record this assembly as done so a later run can skip it
                        Try
                            System.IO.File.AppendAllText(sPhase4CheckpointPath, sPhase4CurrentDocFullName & vbCrLf)
                            oPhase4AlreadyDone.Add(sPhase4CurrentDocFullName)
                        Catch : End Try
                        PeriodicGcTick()
                    Next


                    oLog.Append(vbCrLf & "  Phase 4 done: " & iLiveRepointed & " live occurrence(s) repointed, " & iLiveFailed & " failure(s).")
                    Try : System.IO.File.AppendAllText(sLogFilePath, "Phase 4 done: " & iLiveRepointed & " repointed, " & iLiveFailed & " failed." & vbCrLf) : Catch : End Try
                    If oPhase4Failures.Count > 0 Then
                        oLog.Append(vbCrLf & "  Phase 4 failure list (" & oPhase4Failures.Count & "):")
                        Try : System.IO.File.AppendAllText(sLogFilePath, "Phase 4 failure list:" & vbCrLf) : Catch : End Try
                        For Each sFail As String In oPhase4Failures
                            oLog.Append(vbCrLf & "    " & sFail)
                            Try : System.IO.File.AppendAllText(sLogFilePath, "  " & sFail & vbCrLf) : Catch : End Try
                        Next
                    End If

                    ' --- PHASE 4b: VERIFICATION - report any remaining old-segment refs ---
                    oLog.Append(vbCrLf & "Mode 2 Phase 4b: verifying no old-segment references remain in open tree...")
                    Try : System.IO.File.AppendAllText(sLogFilePath, "Mode 2 Phase 4b: verification scan..." & vbCrLf) : Catch : End Try
                    Dim iStillOld As Integer = 0
                    Try
                        For Each oVDoc As Document In ThisApplication.Documents
                            Try
                                If oVDoc.DocumentType <> kAssemblyDocumentObject Then Continue For
                                Dim sVP As String = oVDoc.FullFileName
                                If Trim(sVP) = "" OrElse IsInExcludedFolder(sVP) Then Continue For
                                ' SAFETY: only verify assemblies inside sTargetFolder.
                                ' Source assemblies are intentionally not repointed by Phase 4;
                                ' reporting them as STILL OLD is a false positive.
                                If Not IsDocSafeToMutate(sVP, sTargetFolder, sTopAssemblyFullName) Then Continue For
                                For Each oVFD As FileDescriptor In oVDoc.File.ReferencedFileDescriptors
                                    Dim sVRef As String = ""
                                    Try : sVRef = oVFD.FullFileName : Catch : Continue For : End Try
                                    If Trim(sVRef) = "" Then Continue For
                                    Dim sVFn As String = System.IO.Path.GetFileName(sVRef)
                                    ' Only report if the CURRENT path is still a map key AND the mapped target is different.
                                    ' Same-name / no-op entries are ignored.
                                    Dim bStill As Boolean = False
                                    If oMode2Map.ContainsKey(sVRef) Then
                                        Dim sMapped As String = oMode2Map(sVRef)
                                        If String.Compare(sVRef, sMapped, True) <> 0 Then bStill = True
                                    ElseIf oNameToNew.ContainsKey(sVFn) Then
                                        Dim sMapped2 As String = oNameToNew(sVFn)
                                        If String.Compare(sVRef, sMapped2, True) <> 0 Then bStill = True
                                    End If
                                    If bStill Then
                                        iStillOld = iStillOld + 1
                                        oLog.Append(vbCrLf & "  STILL OLD: " & sVFn & "  (in " & System.IO.Path.GetFileName(sVP) & ")")
                                        Try : System.IO.File.AppendAllText(sLogFilePath, "  STILL OLD: " & sVFn & "  in " & System.IO.Path.GetFileName(sVP) & vbCrLf) : Catch : End Try
                                    End If
                                Next
                            Catch
                            End Try
                        Next
                    Catch
                    End Try
                    If iStillOld = 0 Then
                        oLog.Append(vbCrLf & "  Phase 4b: CLEAN - no old-segment references remain in open assemblies.")
                        Try : System.IO.File.AppendAllText(sLogFilePath, "Phase 4b: CLEAN" & vbCrLf) : Catch : End Try
                    Else
                        oLog.Append(vbCrLf & "  Phase 4b: " & iStillOld & " old-segment reference(s) still present - see log.")
                        Try : System.IO.File.AppendAllText(sLogFilePath, "Phase 4b: " & iStillOld & " remaining" & vbCrLf) : Catch : End Try
                    End If

                    ' --- PHASE 5: SAVE TOP ASSEMBLY (olds deliberately KEPT) ---
                    ' Leaving olds on disk matches Mode 1 behaviour and avoids
                    ' the "delete then discover a missed parent still pointed
                    ' at the old path" failure mode. A later cleanup pass or
                    ' Mode 5 verify can confirm everything is clean before
                    ' manual deletion.
                    oLog.Append(vbCrLf & "Mode 2 Phase 5: complete. Old files left on disk (safe). Run Mode 5 to verify, then delete olds manually if desired.")
                    Try : System.IO.File.AppendAllText(sLogFilePath, "Phase 5: complete. Olds kept on disk." & vbCrLf) : Catch : End Try
                    bMode2MultiPhaseDone = True
                    ' Free memory before any residual post-work
                    Try : System.IO.File.AppendAllText(sLogFilePath, "Mode 2 multi-phase done - skipping heavy post-passes (crash prevention)." & vbCrLf) : Catch : End Try
                Else
                    oLog.Append(vbCrLf & "Mode 2: nothing to rename - all files already clean.")
                End If
            Else
                ' Modes 1 and 3: single pass as before
                Call ProcessLevel(oAsmDef, sFind, sReplace, bUseContainsMode, sTargetFolder, sTopAssemblyFullName, oLog, iCount, oRenameMap, oSavedInPlace, oVisitedLevels, oPathStack, oProcessedResults, sLogFilePath, , oNeedsCheckout, Nothing, "")
            End If
        End If
    Catch ex As Exception
        oLog.Append(vbCrLf & "FAILED during traversal: " & ex.Message)
        Try
            System.IO.File.AppendAllText(sLogFilePath, vbCrLf & "FAILED during traversal: " & ex.Message & vbCrLf & ex.StackTrace)
        Catch
        End Try
    End Try

AfterSingleTraversal:
    ' ---------- TOP ASSEMBLY PARAM TABLE FIX (Mode 1/2 only) ----------
    ' The top assembly is the ROOT document - never in AllReferencedDocuments.
    ' Fix its param table links and derive sources explicitly here.
    If Not oChoice.bConsolidateOnlyMode Then
        Try
            Dim bTopChanged As Boolean = False
            ' Loop over all batch find tokens so xlsx links matching any prefix are caught.
            ' In Mode 4, sFind = only the first token; other tokens (e.g. PJ174 for
            ' PJ174-MJA49-GT-0-368-00.xlsx) would be missed with a single call.
            Dim oTopFinds As New System.Collections.Generic.List(Of String)
            ' FIX 3c: Mode 6 (Copy Design) sets oBatchFinds but GoTo SkipBatchMode
            ' means bBatchMode is never set True. Guard on oBatchFinds only.
            If oChoice.oBatchFinds IsNot Nothing AndAlso oChoice.oBatchFinds.Count > 0 Then
                oTopFinds.AddRange(oChoice.oBatchFinds)
            Else
                oTopFinds.Add(sFind)
            End If
            For Each sTopFind As String In oTopFinds
                If UpdateLinkedParamsAfterRename(oAsmDoc, oRenameMap, oLog, iCount, sTopFind, sReplace, bUseContainsMode, sTargetFolder, oNeedsCheckout) Then bTopChanged = True
                If oAsmDoc.DocumentType = kPartDocumentObject Then
                    If ProcessDerivedSource(oAsmDoc, sTopFind, sReplace, bUseContainsMode, sTargetFolder, sTopAssemblyFullName, oLog, iCount, oRenameMap, sLogFilePath) Then bTopChanged = True
                End If
            Next
            If bTopChanged Then
                Try
                    Dim oTopAttrs As System.IO.FileAttributes = System.IO.File.GetAttributes(sTopAssemblyFullName)
                    If (oTopAttrs And System.IO.FileAttributes.ReadOnly) = System.IO.FileAttributes.ReadOnly Then System.IO.File.SetAttributes(sTopAssemblyFullName, oTopAttrs And Not System.IO.FileAttributes.ReadOnly)
                Catch
                End Try
                Try : oAsmDoc.Save2(False) : oLog.Append(vbCrLf & "TOP ASSEMBLY param tables updated and saved.") : Catch exTS As Exception : oLog.Append(vbCrLf & "TOP ASSEMBLY param table save FAILED: " & exTS.Message) : End Try
            End If
        Catch exTop As Exception
            oLog.Append(vbCrLf & "TOP ASSEMBLY param table fix FAILED: " & exTop.Message)
        End Try
    End If

    ' ---------- POST-TRAVERSAL DERIVED/PARAM PASS (Mode 1/2 only) ----------
    ' Runs after the main ProcessLevel traversal to catch any parts whose
    ' derived sources or param table links were missed because their parent
    ' assembly was short-circuited by the performance cache. Uses
    ' AllReferencedDocuments so the cache has no effect here.
    ' SKIP after Mode 2 multi-phase: Phases 1-4 already mapped, copied, fixed
    ' internal refs, and repointed the live tree. Re-walking AllReferencedDocuments
    ' and Documents.Open on hundreds of files is what caused Inventor crashes.
    If bMode2MultiPhaseDone Then
        Try : System.IO.File.AppendAllText(sLogFilePath, vbCrLf & "Mode 2: heavy post-passes SKIPPED (already completed in Phases 1-4)." & vbCrLf) : Catch : End Try
        ' --- CROSS-PROJECT DERIVED FIX PASS ---
        ' The pre-built Copy Design map only covers the primary old prefix.
        ' Cross-project old prefixes (e.g. PJ00180, PJ00190) can appear as
        ' DERIVED SOURCES inside ipt files. AllReferencedDocuments on the
        ' assembly does NOT enumerate derived sources — only ProcessDerivedSource
        ' (called by RunDerivedAndParamFixPass) reaches them.
        ' Run a targeted derived pass for each cross-project old prefix in
        ' oBatchFinds, skipping the new prefix (already handled by Phases 1-4).
        Try
            Dim oCrossFinds As New System.Collections.Generic.List(Of String)
            ' FIX 3a: Mode 6 (Copy Design) sets oBatchFinds but GoTo SkipBatchMode
            ' means bBatchMode is never set True. Guard on oBatchFinds only.
            If oChoice.oBatchFinds IsNot Nothing AndAlso oChoice.oBatchFinds.Count > 0 Then
                For Each sBFx As String In oChoice.oBatchFinds
                    If String.Compare(sBFx, sReplace, True) <> 0 Then
                        oCrossFinds.Add(sBFx)
                    End If
                Next
            End If
            If oCrossFinds.Count > 0 Then
                Try : System.IO.File.AppendAllText(sLogFilePath, "Cross-project derived fix pass: " & String.Join(", ", oCrossFinds.ToArray()) & vbCrLf) : Catch : End Try
                For Each sCrossFind As String In oCrossFinds
                    Try
                        RunDerivedAndParamFixPass(oAsmDoc, sCrossFind, sReplace, False, sTargetFolder, oRenameMap, oLog, iCount, oNeedsCheckout, sLogFilePath)
                    Catch exCross As Exception
                        Try : System.IO.File.AppendAllText(sLogFilePath, "Cross-project derived pass FAILED for '" & sCrossFind & "': " & exCross.Message & vbCrLf) : Catch : End Try
                    End Try
                Next
            End If
        Catch exCrossOuter As Exception
            Try : System.IO.File.AppendAllText(sLogFilePath, "Cross-project derived fix outer error: " & exCrossOuter.Message & vbCrLf) : Catch : End Try
        End Try
    ElseIf Not oChoice.bConsolidateOnlyMode Then
        Try
            System.IO.File.AppendAllText(sLogFilePath, vbCrLf & "Starting post-traversal derived/param fix pass." & vbCrLf)
        Catch
        End Try
        Try
            ' Run once per batch find token so ALL prefix variants are caught
            Dim oPassFinds As New System.Collections.Generic.List(Of String)
            ' FIX 3b: Mode 6 (Copy Design) sets oBatchFinds but GoTo SkipBatchMode
            ' means bBatchMode is never set True. Guard on oBatchFinds only.
            If oChoice.oBatchFinds IsNot Nothing AndAlso oChoice.oBatchFinds.Count > 0 Then
                oPassFinds.AddRange(oChoice.oBatchFinds)
            Else
                oPassFinds.Add(sFind)
            End If
            For Each sPassFind As String In oPassFinds
                RunDerivedAndParamFixPass(oAsmDoc, sPassFind, sReplace, bUseContainsMode, sTargetFolder, oRenameMap, oLog, iCount, oNeedsCheckout, sLogFilePath)
            Next
        Catch ex As Exception
            oLog.Append(vbCrLf & "FAILED during post-traversal derived/param pass: " & ex.Message)
            Try
                System.IO.File.AppendAllText(sLogFilePath, vbCrLf & "FAILED during post-traversal derived/param pass: " & ex.Message & vbCrLf & ex.StackTrace)
            Catch
            End Try
        End Try

        ' --- FIX INTERNAL REFS PASS ---
        ' Three-pass fix (param tables, file descriptors, BaseComponent) applied
        ' to every document in the tree using each document's OWN FOLDER as target.
        ' This catches xlsx/derive links that RunDerivedAndParamFixPass misses
        ' (e.g. Frame Generator xlsx sitting in subfolders alongside frame members).
        Try
            System.IO.File.AppendAllText(sLogFilePath, vbCrLf & "Starting fix-internal-refs pass." & vbCrLf)
        Catch
        End Try
        Try
            RunFixInternalRefsPass(oAsmDoc, sFind, sReplace, bUseContainsMode, sTargetFolder, oRenameMap, oLog, iCount, sLogFilePath)
        Catch ex As Exception
            oLog.Append(vbCrLf & "FAILED during fix-internal-refs pass: " & ex.Message)
        End Try
    End If

    ' ---------- PJ-NUMBER PROPERTY SYNC (new pass, runs after the main traversal) ----------
    ' Separate from ProcessLevel deliberately - this walks the tree via
    ' Inventor's own AllReferencedDocuments (which handles dedup/cycles
    ' itself) rather than adding more branches to the already-hardened
    ' recursive traversal above. Extracts a "PJ<digits>" style project
    ' number from the REPLACE text (falling back to the FIND text, which
    ' is the same value in the "localize without renaming" case) and, for
    ' every referenced part/sub-assembly whose file name now contains that
    ' number, normalizes any "PJ<digits>" token found inside its Part
    ' Number or SPECIFICATION property to match - regardless of what the
    ' old number in there actually was. If neither Find nor Replace
    ' contains a PJ-style number at all (e.g. a plain segment swap with
    ' nothing project-related), this pass does nothing.
    Dim sCurrentPjNumber As String = ExtractPjNumber(sReplace)
    If sCurrentPjNumber = "" Then sCurrentPjNumber = ExtractPjNumber(sFind)
    Dim iPropsUpdated As Integer = 0

    If sCurrentPjNumber <> "" Then
        Try
            System.IO.File.AppendAllText(sLogFilePath, vbCrLf & "Starting PJ-number property sync pass - current PJ number: '" & sCurrentPjNumber & "'" & vbCrLf)
        Catch
        End Try
        Try
            RunPjPropertySyncPass(oAsmDoc, sCurrentPjNumber, oChoice.oSegFinds, oChoice.oSegReplaces, oLog, iPropsUpdated)
        Catch ex As Exception
            oLog.Append(vbCrLf & "FAILED during PJ-number property sync pass: " & ex.Message)
            Try
                System.IO.File.AppendAllText(sLogFilePath, vbCrLf & "FAILED during PJ-number property sync pass: " & ex.Message & vbCrLf & ex.StackTrace)
            Catch
            End Try
        End Try
    Else
        oLog.Append(vbCrLf & "PJ-number property sync SKIPPED - no 'PJ' + digits pattern found in the Find or Replace text.")
    End If

    ' ---------- Save the main assembly with its updated references ----------
    ' Only save if something actually changed (iCount > 0). If nothing was
    ' successfully repointed there is no point saving - the assembly is
    ' unchanged in memory and a Save() call only risks triggering Vault
    ' E_FAIL errors on checked-in files unnecessarily.
    If iCount > 0 Then
        ' Clear read-only on the top assembly before saving - File.Copy'd
        ' assemblies inherit the read-only flag from Vault source files.
        Try
            Dim oTopAttrs As System.IO.FileAttributes = System.IO.File.GetAttributes(oAsmDoc.FullFileName)
            If (oTopAttrs And System.IO.FileAttributes.ReadOnly) = System.IO.FileAttributes.ReadOnly Then
                System.IO.File.SetAttributes(oAsmDoc.FullFileName, oTopAttrs And Not System.IO.FileAttributes.ReadOnly)
            End If
        Catch
        End Try
        Try
            oAsmDoc.Update()
            oAsmDoc.Save()
        Catch ex As Exception
            oLog.Append(vbCrLf & vbCrLf & "WARNING: FAILED to save/update the top assembly after renaming: " & ex.Message & vbCrLf & "All the individual renames above should still have gone through, but the TOP ASSEMBLY itself may not be saved to disk. If this is a generic error, check whether the file is checked IN (read-only) in Vault rather than checked out - that's the most common cause. Check it out and save manually (File > Save) once it is.")
            Try
                System.IO.File.AppendAllText(sLogFilePath, vbCrLf & "FAILED to save/update top assembly: " & ex.Message & vbCrLf & ex.StackTrace)
            Catch
            End Try
        End Try
    Else
        oLog.Append(vbCrLf & vbCrLf & "SAVE SKIPPED: no occurrences were successfully repointed this run - assembly unchanged, save not needed.")
    End If

    ' ---------- BROWSER NODE RESET PASS ----------
    ' Resets every occurrence's browser display name to its actual
    ' filename, clearing stale Vault Copy Design labels (e.g.
    ' "PJ00145-...:2") so the browser shows the correct renamed names.
    ' Runs after all saves so it doesn't interfere with save logic.
    Dim iBrowserReset As Integer = 0
    Try
        System.IO.File.AppendAllText(sLogFilePath, vbCrLf & "Starting browser node reset pass." & vbCrLf)
    Catch
    End Try
    Try
        RunBrowserNodeResetPass(oAsmDef, iBrowserReset)
        oLog.Append(vbCrLf & "Browser node names reset: " & iBrowserReset & " occurrence(s) updated.")
    Catch ex As Exception
        oLog.Append(vbCrLf & "Browser node reset FAILED: " & ex.Message)
    End Try

    ' ---------- DRAWING UPDATE PASS (Mode 6 only, when user opted in) ----------
    ' Runs BEFORE document cleanup so all renamed model documents are still
    ' live in session - ReplaceReference requires both old and new Document
    ' objects to be open at call time.
    ' Drawing update always runs in this rule (bUpdateDrawings=True, sDrawingsFolder auto-set).
    ' Gate: bCopyDesignMode confirms we're in the right rule; bUpdateDrawings=False signals
    ' Phase 0 found no drawings (already logged above) — skip gracefully in that case.
    If oChoice.bCopyDesignMode AndAlso oChoice.bUpdateDrawings AndAlso Trim(oChoice.sDrawingsFolder) <> "" Then
        ' --- Drawing selection checkpoint ---
        ' Show all .idw files in the auto-detected drawings folder with checkboxes so the
        ' user can choose exactly which drawings to update. Useful for partial re-runs.
        Dim oSelectedDrawings As System.Collections.Generic.List(Of String) = Nothing
        Try
            oSelectedDrawings = ShowDrawingSelectionForm(oChoice.sDrawingsFolder, oRenameMap, oPhase0Data)
        Catch ex As Exception
            oLog.Append(vbCrLf & "DRAW-SELECT-FORM-ERROR: " & ex.Message)
        End Try
        ' Nothing returned = user cancelled
        If oSelectedDrawings Is Nothing Then
            oLog.Append(vbCrLf & "Drawing update pass CANCELLED by user.")
            Try : System.IO.File.AppendAllText(sLogFilePath, vbCrLf & "Drawing update pass cancelled by user." & vbCrLf) : Catch : End Try
        ElseIf oSelectedDrawings.Count = 0 Then
            oLog.Append(vbCrLf & "Drawing update pass SKIPPED - no drawings selected.")
            Try : System.IO.File.AppendAllText(sLogFilePath, vbCrLf & "Drawing update pass skipped - no drawings selected." & vbCrLf) : Catch : End Try
        Else
            Dim iDwgOk As Integer = 0
            Dim iDwgPartial As Integer = 0
            Dim iDwgFail As Integer = 0
            Try
                System.IO.File.AppendAllText(sLogFilePath, vbCrLf & "Starting drawing update pass. " & oSelectedDrawings.Count & " drawing(s) selected. Folder: " & oChoice.sDrawingsFolder & vbCrLf)
            Catch
            End Try
            Try
                RunDrawingUpdatePass(oSelectedDrawings, oRenameMap, oChoice.oDrawingStateMatch, oLog, iDwgOk, iDwgPartial, iDwgFail, sLogFilePath)
            Catch ex As Exception
                oLog.Append(vbCrLf & "DRAWING UPDATE PASS FAILED: " & ex.Message)
                Try
                    System.IO.File.AppendAllText(sLogFilePath, vbCrLf & "DRAWING UPDATE PASS FAILED: " & ex.Message & vbCrLf & ex.StackTrace)
                Catch
                End Try
            End Try
            oLog.Append(vbCrLf & "Drawing update pass complete: " & iDwgOk & " saved, " & iDwgPartial & " partial (not saved - manual repair needed), " & iDwgFail & " failed to open.")
            Try
                System.IO.File.AppendAllText(sLogFilePath, vbCrLf & "Drawing update pass complete: " & iDwgOk & " saved, " & iDwgPartial & " partial, " & iDwgFail & " failed." & vbCrLf)
            Catch
            End Try
        End If
    End If

    ' ---------- POST-SWEEP DRAWING UPDATE PROMPT ----------
    ' Prefer the drawings folder already captured at rule start (from the
    ' launching drawing). Only browse if we truly don't know it.
    If Not oChoice.bUpdateDrawings AndAlso bMode2MultiPhaseDone Then
        Try
            Dim sKnownDwgFolder As String = ""
            If Trim(oChoice.sDrawingsFolder) <> "" AndAlso System.IO.Directory.Exists(oChoice.sDrawingsFolder) Then
                sKnownDwgFolder = oChoice.sDrawingsFolder
            End If

            Dim sDwgPromptResult As DialogResult = MessageBox.Show(
                "Sweep complete." & vbCrLf & vbCrLf &
                "Would you like to update drawings now?" & vbCrLf &
                If(sKnownDwgFolder <> "",
                   "(Using the drawings folder already detected from the launching drawing:" & vbCrLf & sKnownDwgFolder & ")",
                   "(You will be asked to select the drawings folder.)"),
                "Update Drawings?",
                MessageBoxButtons.YesNo,
                MessageBoxIcon.Question)
            If sDwgPromptResult = DialogResult.Yes Then
                Dim sBrowsedDwgFolder As String = sKnownDwgFolder

                ' Only browse if we don't already know the folder
                If sBrowsedDwgFolder = "" Then
                    ' Auto-probe sibling folders of sTargetFolder for a drawings folder
                    Dim sAutoDrawingFolder As String = ""
                    Try
                        Dim sParent As String = System.IO.Path.GetDirectoryName(sTargetFolder)
                        Dim oDwgCandidates As String() = {"Drawings", "Drawing", "DWG", "IDW", "drawings", "drawing"}
                        For Each sCandidate As String In oDwgCandidates
                            Dim sCandPath As String = System.IO.Path.Combine(sParent, sCandidate)
                            If System.IO.Directory.Exists(sCandPath) Then
                                Dim oCandFiles As String() = System.IO.Directory.GetFiles(sCandPath, "*.idw")
                                If oCandFiles.Length = 0 Then oCandFiles = System.IO.Directory.GetFiles(sCandPath, "*.dwg")
                                If oCandFiles.Length > 0 Then
                                    sAutoDrawingFolder = sCandPath
                                    Exit For
                                End If
                            End If
                        Next
                    Catch : End Try
                    sBrowsedDwgFolder = sAutoDrawingFolder
                    If sBrowsedDwgFolder = "" Then
                        Dim oBrowse As New System.Windows.Forms.FolderBrowserDialog()
                        oBrowse.Description = "Select the folder containing the drawings (.idw files) to update"
                        oBrowse.ShowNewFolderButton = False
                        Try
                            Dim sModelParent As String = System.IO.Path.GetDirectoryName(sTargetFolder)
                            If System.IO.Directory.Exists(sModelParent) Then oBrowse.SelectedPath = sModelParent
                        Catch : End Try
                        If oBrowse.ShowDialog() <> DialogResult.OK OrElse Trim(oBrowse.SelectedPath) = "" Then
                            oLog.Append(vbCrLf & "Post-sweep drawing update: folder browse cancelled.")
                            GoTo SkipPostSweepDrawings
                        End If
                        sBrowsedDwgFolder = oBrowse.SelectedPath
                    End If
                End If

                If True Then  ' scope block
                    oChoice.sDrawingsFolder = sBrowsedDwgFolder
                    oChoice.bUpdateDrawings = True
                    Try : System.IO.File.AppendAllText(sLogFilePath, vbCrLf & "Post-sweep drawing update: using folder: " & sBrowsedDwgFolder & vbCrLf) : Catch : End Try
                    ' Show drawing selection form so user can pick which .idw files to update
                    Dim oPostDwgSelected As System.Collections.Generic.List(Of String) = Nothing
                    Try
                        oPostDwgSelected = ShowDrawingSelectionForm(sBrowsedDwgFolder, oRenameMap, Nothing)
                    Catch ex As Exception
                        oLog.Append(vbCrLf & "POST-SWEEP DRAW-SELECT-FORM-ERROR: " & ex.Message)
                    End Try
                    If oPostDwgSelected Is Nothing Then
                        oLog.Append(vbCrLf & "Post-sweep drawing update CANCELLED by user.")
                        Try : System.IO.File.AppendAllText(sLogFilePath, "Post-sweep drawing update cancelled." & vbCrLf) : Catch : End Try
                    ElseIf oPostDwgSelected.Count = 0 Then
                        oLog.Append(vbCrLf & "Post-sweep drawing update SKIPPED — no drawings selected.")
                        Try : System.IO.File.AppendAllText(sLogFilePath, "Post-sweep drawing update skipped - no drawings selected." & vbCrLf) : Catch : End Try
                    Else
                        Dim iPostDwgOk As Integer = 0, iPostDwgPartial As Integer = 0, iPostDwgFail As Integer = 0
                        Try
                            RunDrawingUpdatePass(oPostDwgSelected, oRenameMap, oChoice.oDrawingStateMatch, oLog, iPostDwgOk, iPostDwgPartial, iPostDwgFail, sLogFilePath)
                        Catch exPostDwg As Exception
                            oLog.Append(vbCrLf & "POST-SWEEP DRAWING UPDATE FAILED: " & exPostDwg.Message)
                            Try : System.IO.File.AppendAllText(sLogFilePath, "Post-sweep drawing update FAILED: " & exPostDwg.Message & vbCrLf) : Catch : End Try
                        End Try
                        oLog.Append(vbCrLf & "Post-sweep drawing update: " & iPostDwgOk & " saved, " & iPostDwgPartial & " partial, " & iPostDwgFail & " failed.")
                        Try : System.IO.File.AppendAllText(sLogFilePath, "Post-sweep drawing update complete: " & iPostDwgOk & " saved, " & iPostDwgPartial & " partial, " & iPostDwgFail & " failed." & vbCrLf) : Catch : End Try
                    End If
                End If  ' If True scope block
SkipPostSweepDrawings:
            Else
                oLog.Append(vbCrLf & "Post-sweep drawing update skipped by user.")
                Try : System.IO.File.AppendAllText(sLogFilePath, "Post-sweep drawing update skipped by user." & vbCrLf) : Catch : End Try
            End If
        Catch exDwgPrompt As Exception
            Try : System.IO.File.AppendAllText(sLogFilePath, "Post-sweep drawing prompt error: " & exDwgPrompt.Message & vbCrLf) : Catch : End Try
        End Try
    End If

    ' ---------- Restore Excel dialog behaviour ----------
    Try
        If oExcelApp IsNot Nothing Then
            oExcelApp.DisplayAlerts = bExcelAlertsOriginal
            If bExcelCreatedHere Then Try : oExcelApp.Quit() : Catch : End Try
        End If
    Catch
    End Try

    ' ---------- CLEANUP: close documents opened by the rule ----------
    ' Close any document that was NOT in the initial session snapshot
    ' (i.e. we opened it during the run), is not the top assembly, and
    ' is not dirty. This is the primary defence against the multi-GB
    ' memory balloon and against Inventor trying to save SKEL/FG files
    ' on session close.
    Try
        Dim oInitOpen As System.Collections.Generic.HashSet(Of String) = GetSetInitiallyOpenDocs()
        Dim oDocsToClose As New System.Collections.Generic.List(Of Document)
        For Each oOpenDoc As Document In ThisApplication.Documents
            Try
                Dim sDocPath As String = ""
                Try : sDocPath = oOpenDoc.FullFileName : Catch : Continue For : End Try
                If Trim(sDocPath) = "" Then Continue For
                If String.Compare(sDocPath, sTopAssemblyFullName, True) = 0 Then Continue For
                ' Keep anything that was already open when the rule started
                If oInitOpen.Contains(sDocPath) Then Continue For
                Dim bDirty As Boolean = False
                Try : bDirty = oOpenDoc.Dirty : Catch : End Try
                If Not bDirty Then oDocsToClose.Add(oOpenDoc)
            Catch
            End Try
        Next
        Dim iClosed As Integer = 0
        For Each oCloseDoc As Document In oDocsToClose
            Try
                oCloseDoc.Close(False)
                iClosed = iClosed + 1
            Catch
            End Try
        Next
        If iClosed > 0 Then
            oLog.Append(vbCrLf & "Closed " & iClosed & " rule-opened document(s) to free memory / prevent session save conflicts.")
            Try : System.IO.File.AppendAllText(sLogFilePath, vbCrLf & "Closed " & iClosed & " rule-opened document(s)." & vbCrLf) : Catch : End Try
        End If
    Catch exClose As Exception
        Try : System.IO.File.AppendAllText(sLogFilePath, vbCrLf & "Cleanup close pass failed: " & exClose.Message & vbCrLf) : Catch : End Try
    End Try

    ' ---------- Restore Inventor's normal dialog behaviour ----------
    ThisApplication.SilentOperation = bOrigSilent

    Try
        System.IO.File.AppendAllText(sLogFilePath, vbCrLf & vbCrLf & "Rule finished: " & DateTime.Now.ToString())
    Catch
    End Try

    ' --- CHECKOUT NOTE (log only - no blocking popup) ---
    ' Files whose param table links could not be repointed because Vault
    ' intercepted the COM call are noted in the decisions log and included
    ' in the final summary. No blocking popup - the rule handles these
    ' gracefully on re-runs once the files are in the correct local state.
    If oNeedsCheckout.Count > 0 Then
        oLog.Append(vbCrLf & vbCrLf & "NOTE: " & oNeedsCheckout.Count & " file(s) had param table links that could not be repointed this run")
        oLog.Append(vbCrLf & "(Vault intercepted the COM call - these will be retried automatically on the next run):")
        For Each sCoPath As String In oNeedsCheckout
            oLog.Append(vbCrLf & "  " & System.IO.Path.GetFileName(sCoPath))
        Next
        Try
            System.IO.File.AppendAllText(sLogFilePath, vbCrLf & "NOTE - param table repoint deferred for " & oNeedsCheckout.Count & " file(s) - will retry on next run." & vbCrLf)
        Catch
        End Try
    End If

    ' ---------- PASS MANIFEST ----------
    ' Write a clean old-path -> new-path table to the assembly folder.
    ' Auto-numbered _Pass1, _Pass2, … so every run is preserved side by side.
    Dim sManifestPath As String = ""
    Try
        sManifestPath = WritePassManifest(sTargetFolder, _
            System.IO.Path.GetFileNameWithoutExtension(sTopAssemblyFullName), _
            oRenameMap, oLog)
    Catch ex As Exception
        oLog.Append(vbCrLf & "MANIFEST-WARN: could not write pass manifest: " & ex.Message)
    End Try

    Dim sTotalElapsed As String = ""
    Try
        Dim tsElapsed As TimeSpan = DateTime.Now - dRuleStartTime
        sTotalElapsed = "  (" & CInt(Math.Floor(tsElapsed.TotalMinutes)).ToString & " min " & tsElapsed.Seconds.ToString & " sec)"
    Catch : End Try
    MessageBox.Show(
        "🎉  CONGRATULATIONS — YOUR CLEAN SWEEP IS DONE!" & vbCrLf &
        "    Project: " & sReplace & sTotalElapsed & vbCrLf &
        String.Empty.PadRight(60, "─"c) & vbCrLf &
        oLog.ToString(),
        "✅  Clean Sweep Complete — " & sReplace)
    ' Save the assembly (not ThisDoc, which may be the GA drawing if launched from it)
    Try
        oAsmDoc.Save()
    Catch exSave As Exception
        oLog.Append(vbCrLf & "SAVE-WARN: final assembly save failed: " & exSave.Message)
    End Try

    ' ---------- Post-run window activation ----------
    ' Inventor's SaveAs() activates each newly saved document during the traverse,
    ' so by the end the last-saved file is the active window.
    '
    ' Strategy: activate the NEW top-assembly copy so it is front-and-centre for
    ' inspection. The originating GA drawing stays open in the background — it is
    ' never closed by this rule. If the new copy cannot be found/activated, fall
    ' back to re-activating the GA drawing instead.
    Dim bActivatedNewCopy As Boolean = False
    Try
        Dim sNewTopAsmFull As String = ""
        If oRenameMap.TryGetValue(sTopAssemblyFullName, sNewTopAsmFull) AndAlso _
           Trim(sNewTopAsmFull) <> "" AndAlso _
           System.IO.File.Exists(sNewTopAsmFull) Then
            ' Look for it in the open-documents collection first (faster, no COM open call).
            For Each oOpenDoc As Document In ThisApplication.Documents
                Try
                    If String.Equals(oOpenDoc.FullFileName, sNewTopAsmFull, StringComparison.OrdinalIgnoreCase) Then
                        oOpenDoc.Activate()
                        bActivatedNewCopy = True
                        Exit For
                    End If
                Catch
                End Try
            Next
            ' If it was closed after SaveAs, open it now.
            If Not bActivatedNewCopy Then
                Try
                    Dim oNewTopDoc As Document = ThisApplication.Documents.Open(sNewTopAsmFull, False)
                    If oNewTopDoc IsNot Nothing Then
                        oNewTopDoc.Activate()
                        bActivatedNewCopy = True
                    End If
                Catch
                End Try
            End If
        End If
    Catch
    End Try

    ' Fallback: bring the GA drawing back if we couldn't activate the new copy.
    If Not bActivatedNewCopy AndAlso oOriginatingDrawing IsNot Nothing Then
        Try
            oOriginatingDrawing.Activate()
        Catch
        End Try
    End If

End Sub

' =====================================================================
' DRAWING SELECTION FORM
' =====================================================================
' Shows a checklist of all .idw files in sDrawingsFolder.
' Drawings that have at least one reference in oRenameMap are pre-ticked.
' Drawings with no matching references are shown un-ticked (grey label) but
' selectable — handy for confirming the map is correct even on a no-op drawing.
' Returns Nothing if the user cancels, or a List(Of String) of selected full paths.
' =====================================================================
Function ShowDrawingSelectionForm( _
    sDrawingsFolder As String, _
    oRenameMap As System.Collections.Generic.Dictionary(Of String, String), _
    oPhase0Data As System.Collections.Generic.List(Of Object())) _
    As System.Collections.Generic.List(Of String)

    ' Collect both Inventor native (.idw) and Inventor DWG (.dwg) drawing files.
    Dim oIdwFiles As New System.Collections.Generic.List(Of String)
    Try
        oIdwFiles.AddRange(System.IO.Directory.GetFiles(sDrawingsFolder, "*.idw"))
        oIdwFiles.AddRange(System.IO.Directory.GetFiles(sDrawingsFolder, "*.dwg"))
    Catch
        Return Nothing
    End Try
    If oIdwFiles.Count = 0 Then
        MessageBox.Show("No drawing files (.idw / .dwg) found in:" & vbCrLf & sDrawingsFolder, "Drawing Update")
        Return New System.Collections.Generic.List(Of String)()
    End If

    ' Sort ascending so GA (lowest number) appears first
    oIdwFiles.Sort()

    ' --- Phase 0 authoritative set ---
    ' Only drawings that appeared in the Phase 0 scan (i.e. were presented in the
    ' drawing model rename form) are candidates for pre-ticking. Any .idw in the
    ' folder that was NOT in Phase 0 — obsolete copies, sheets added after the scan —
    ' appears in the list but starts un-ticked regardless of rename-map matches.
    Dim oPhase0Basenames As New System.Collections.Generic.HashSet(Of String)(StringComparer.OrdinalIgnoreCase)
    If oPhase0Data IsNot Nothing Then
        For Each oEntry As Object() In oPhase0Data
            oPhase0Basenames.Add(CStr(oEntry(0)))   ' entry(0) = drawing basename WITH extension
        Next
    End If

    ' --- determine which drawings have matching refs (for pre-tick) ---
    ' A drawing is pre-ticked only if it was in Phase 0 AND has at least one
    ' reference in oRenameMap. Drawings outside Phase 0 are shown greyed/unticked.
    '
    ' Disable event-driven rules at APPLICATION level before ANY Documents.Open.
    ' Event-driven rules (e.g. "Working Drawing Stamp") fire DURING Documents.Open —
    ' setting DisableEventRules on the doc after open is too late and produces a
    ' modal error dialog that blocks the rule and hides behind other windows.
    ' Application-level disable prevents ALL iLogic event rules from firing across
    ' all documents until we restore it. Restored after the scan loop below.
    Try : ThisApplication.iLogicVb.EventRuleManager.DisableEventRules = True : Catch : End Try

    Dim oHasMatch As New System.Collections.Generic.HashSet(Of String)(StringComparer.OrdinalIgnoreCase)
    If oRenameMap IsNot Nothing Then
        For Each sIdw As String In oIdwFiles
            Dim sBasenameChk As String = System.IO.Path.GetFileName(sIdw)
            ' Skip pre-tick scan for drawings not in Phase 0 set
            If oPhase0Basenames.Count > 0 AndAlso Not oPhase0Basenames.Contains(sBasenameChk) Then
                Continue For
            End If
            Dim oDwgDoc As DrawingDocument = Nothing
            Try
                Dim bWasOpen As Boolean = False
                Try
                    oDwgDoc = TryCast(ThisApplication.Documents.ItemByName(sIdw), DrawingDocument)
                    If oDwgDoc IsNot Nothing Then bWasOpen = True
                Catch
                End Try
                If oDwgDoc Is Nothing Then
                    Try
                        oDwgDoc = TryCast(ThisApplication.Documents.Open(sIdw, False), DrawingDocument)
                    Catch
                    End Try
                End If
                If oDwgDoc IsNot Nothing Then
                    For Each oRef As Document In oDwgDoc.ReferencedDocuments
                        Dim sRefPath As String = ""
                        Try : sRefPath = oRef.FullDocumentName : Catch : Continue For : End Try
                        If oRenameMap.ContainsKey(sRefPath) Then
                            oHasMatch.Add(sIdw)
                            Exit For
                        End If
                    Next
                    If Not bWasOpen Then Try : oDwgDoc.Close(False) : Catch : End Try
                End If
            Catch
                If oDwgDoc IsNot Nothing Then Try : oDwgDoc.Close(False) : Catch : End Try
            End Try
        Next
    End If
    ' Restore event rules after the scan loop — form dialogs (the drawing selection form
    ' shown next) must not suppress event rules; only document-open phases need the guard.
    Try : ThisApplication.iLogicVb.EventRuleManager.DisableEventRules = False : Catch : End Try

    ' --- build form ---
    Dim oForm As New System.Windows.Forms.Form()
    oForm.Text = "Drawing Update — Select Drawings to Update"
    oForm.Width = 620
    oForm.FormBorderStyle = System.Windows.Forms.FormBorderStyle.FixedDialog
    oForm.MaximizeBox = False
    oForm.StartPosition = System.Windows.Forms.FormStartPosition.CenterScreen

    ' Header label
    Dim oLblHdr As New System.Windows.Forms.Label()
    oLblHdr.Text = "Select which drawings to update with the new model references."
    oLblHdr.Left = 12 : oLblHdr.Top = 10 : oLblHdr.Width = 580 : oLblHdr.Height = 18
    oForm.Controls.Add(oLblHdr)

    Dim oLblSub As New System.Windows.Forms.Label()
    oLblSub.Text = "Pre-ticked = in drawing model map with matching refs.  Grey = not in original scan / no matches."
    oLblSub.Left = 12 : oLblSub.Top = 30 : oLblSub.Width = 580 : oLblSub.Height = 18
    oForm.Controls.Add(oLblSub)

    ' Select All / Deselect All buttons (inline row)
    Dim oBtnAll As New System.Windows.Forms.Button()
    oBtnAll.Text = "Select All" : oBtnAll.Left = 12 : oBtnAll.Top = 54 : oBtnAll.Width = 90 : oBtnAll.Height = 24
    oForm.Controls.Add(oBtnAll)

    Dim oBtnNone As New System.Windows.Forms.Button()
    oBtnNone.Text = "Deselect All" : oBtnNone.Left = 108 : oBtnNone.Top = 54 : oBtnNone.Width = 90 : oBtnNone.Height = 24
    oForm.Controls.Add(oBtnNone)

    Dim oBtnMatched As New System.Windows.Forms.Button()
    oBtnMatched.Text = "Matched Only" : oBtnMatched.Left = 204 : oBtnMatched.Top = 54 : oBtnMatched.Width = 100 : oBtnMatched.Height = 24
    oForm.Controls.Add(oBtnMatched)

    ' Scrollable checklist panel
    Dim oPanel As New System.Windows.Forms.Panel()
    oPanel.Left = 12 : oPanel.Top = 86 : oPanel.Width = 578 : oPanel.Height = 320
    oPanel.AutoScroll = True
    oPanel.BorderStyle = System.Windows.Forms.BorderStyle.FixedSingle
    oForm.Controls.Add(oPanel)

    Dim oCheckList As New System.Collections.Generic.List(Of System.Windows.Forms.CheckBox)()
    Dim iY As Integer = 4
    For Each sIdw As String In oIdwFiles
        Dim sBasenameRow As String = System.IO.Path.GetFileName(sIdw)
        Dim bMatched As Boolean = oHasMatch.Contains(sIdw)
        Dim bInPhase0 As Boolean = (oPhase0Basenames.Count = 0) OrElse oPhase0Basenames.Contains(sBasenameRow)

        Dim oChk As New System.Windows.Forms.CheckBox()
        oChk.Left = 6 : oChk.Top = iY : oChk.Width = 550 : oChk.Height = 20
        oChk.Tag = sIdw   ' store full path

        If bMatched Then
            ' In Phase 0 AND has rename-map refs — pre-ticked, normal colour
            oChk.Text = sBasenameRow
            oChk.Checked = True
        ElseIf bInPhase0 Then
            ' In Phase 0 but no matching refs in rename map — in drawing set, nothing to swap
            oChk.Text = sBasenameRow & "  (no matching refs in this run)"
            oChk.Checked = False
        Else
            ' Not in Phase 0 — orphan / obsolete / added after scan
            oChk.Text = sBasenameRow & "  (not in original drawing scan)"
            oChk.Checked = False
        End If

        oPanel.Controls.Add(oChk)
        oCheckList.Add(oChk)
        iY = iY + 22
    Next

    ' Resize form height to fit nicely (cap at 600px usable)
    Dim iListHeight As Integer = Math.Min(iY + 12, 400)
    oPanel.Height = iListHeight
    oForm.Height = 86 + iListHeight + 60  ' panel top + panel height + button strip + border

    ' Count label (updates on tick/untick)
    Dim oLblCount As New System.Windows.Forms.Label()
    oLblCount.Left = 12 : oLblCount.Top = oPanel.Top + oPanel.Height + 6
    oLblCount.Width = 300 : oLblCount.Height = 18
    oForm.Controls.Add(oLblCount)

    Dim UpdateCount As Action = Sub()
        Dim n As Integer = 0
        For Each c As System.Windows.Forms.CheckBox In oCheckList
            If c.Checked Then n = n + 1
        Next
        oLblCount.Text = n.ToString & " of " & oIdwFiles.Count & " drawing(s) selected"
    End Sub
    UpdateCount()

    For Each oChk As System.Windows.Forms.CheckBox In oCheckList
        AddHandler oChk.CheckedChanged, Sub() UpdateCount()
    Next

    ' Wire Select All / Deselect All / Matched Only
    AddHandler oBtnAll.Click, Sub()
        For Each c As System.Windows.Forms.CheckBox In oCheckList : c.Checked = True : Next
    End Sub
    AddHandler oBtnNone.Click, Sub()
        For Each c As System.Windows.Forms.CheckBox In oCheckList : c.Checked = False : Next
    End Sub
    AddHandler oBtnMatched.Click, Sub()
        For Each c As System.Windows.Forms.CheckBox In oCheckList
            c.Checked = oHasMatch.Contains(CStr(c.Tag))
        Next
    End Sub

    ' OK / Cancel
    Dim iBtnTop As Integer = oPanel.Top + oPanel.Height + 30
    Dim oBtnOK As New System.Windows.Forms.Button()
    oBtnOK.Text = "Update Selected Drawings" : oBtnOK.Left = 12 : oBtnOK.Top = iBtnTop
    oBtnOK.Width = 200 : oBtnOK.Height = 28
    ' Note: System.Drawing.Color.FromArgb not available in iLogic sandbox - use default button colours
    oBtnOK.DialogResult = System.Windows.Forms.DialogResult.OK
    oForm.Controls.Add(oBtnOK)
    oForm.AcceptButton = oBtnOK

    Dim oBtnSkip As New System.Windows.Forms.Button()
    oBtnSkip.Text = "Skip Drawing Update" : oBtnSkip.Left = 220 : oBtnSkip.Top = iBtnTop
    oBtnSkip.Width = 160 : oBtnSkip.Height = 28
    oBtnSkip.DialogResult = System.Windows.Forms.DialogResult.No
    oForm.Controls.Add(oBtnSkip)

    Dim oBtnCancel As New System.Windows.Forms.Button()
    oBtnCancel.Text = "Cancel Rule" : oBtnCancel.Left = 388 : oBtnCancel.Top = iBtnTop
    oBtnCancel.Width = 100 : oBtnCancel.Height = 28
    oBtnCancel.DialogResult = System.Windows.Forms.DialogResult.Cancel
    oForm.Controls.Add(oBtnCancel)
    oForm.CancelButton = oBtnCancel

    oForm.Height = iBtnTop + 28 + 48  ' final height

    Dim oResult As System.Windows.Forms.DialogResult = oForm.ShowDialog()
    oForm.Dispose()

    If oResult = System.Windows.Forms.DialogResult.Cancel Then
        ' Cancel rule entirely - propagate Nothing to caller
        Return Nothing
    ElseIf oResult = System.Windows.Forms.DialogResult.No Then
        ' Skip drawing update but don't cancel - return empty list
        Return New System.Collections.Generic.List(Of String)()
    End If

    ' OK - collect checked paths
    Dim oSelected As New System.Collections.Generic.List(Of String)()
    For Each oChk As System.Windows.Forms.CheckBox In oCheckList
        If oChk.Checked Then oSelected.Add(CStr(oChk.Tag))
    Next
    Return oSelected

End Function


' =====================================================================
' DRAWING UPDATE PASS
' =====================================================================
' Loops every .idw in sDrawingsFolder (flat - no recursion).
' For each drawing, looks up each of its model references in oRenameMap.
' Calls ReplaceReference for every hit.
'
' SAFETY RULE: only saves a drawing if ALL its model references resolved
' after the pass. A drawing with any remaining unresolved (old-path)
' reference is logged as DRAW-PARTIAL-SKIP and left untouched.
' This prevents silent partial-success drawings passing review.
'
' Requires: all renamed model documents still open in current Inventor
' session (i.e. called BEFORE the document cleanup pass).
' =====================================================================
' =====================================================================
' DRAWING COPY MODE  (launched from a drawing document)
' =====================================================================
' Fast, surgical copy-design for the "run from drawing" path.
' Does NOT traverse sub-assembly trees.
' Steps:
'   1. Collect all model files directly referenced by oDwgDoc
'   2. Folder picker  →  new prefix config form (with re-run detection)
'   3. File.Copy each model to target folder with renamed basename
'   4. Open each copy so it is live in session
'   5. ReplaceReference on oDwgDoc for each old→new pair
'   6. Save drawing
' =====================================================================

' =====================================================================
' WALK TREE TO LOG
' Recursive helper used by PRE/POST tree grabs inside RunDrawingCopyMode.
' Mirrors the standalone Pre/Post Rule Subs Tree Grab iLogic rules.
' Declared BEFORE RunDrawingCopyMode so iLogic compiler resolves the call.
' Pure read-only — nothing is changed, opened extra, or saved.
' =====================================================================
Sub WalkTreeToLog(oOccs As Object, iDepth As Integer, sOutputPath As String, ByRef iCount As Integer)
    Dim sIndent As String = New String(" "c, iDepth * 3)
    For Each oOcc As ComponentOccurrence In oOccs
        Dim sLine As String
        Dim sSuppressed As String = If(oOcc.Suppressed, " [SUPPRESSED]", "")
        Try
            Dim oDoc As Document = oOcc.Definition.Document
            Dim sFull As String = oDoc.FullFileName
            If Trim(sFull) = "" OrElse sFull.Contains("*") Then
                sLine = sIndent & "[VIRTUAL]  " & oOcc.Name & sSuppressed
            Else
                sLine = sIndent & sFull & sSuppressed
            End If
        Catch
            sLine = sIndent & "[NO PATH - virtual or inaccessible]  " & oOcc.Name & sSuppressed
        End Try
        iCount = iCount + 1
        Try : System.IO.File.AppendAllText(sOutputPath, sLine & vbCrLf) : Catch : End Try
        Try
            WalkTreeToLog(oOcc.SubOccurrences, iDepth + 1, sOutputPath, iCount)
        Catch
            ' Part occurrences have no SubOccurrences — expected, ignore
        End Try
    Next
End Sub

' ═══════════════════════════════════════════════════════════════════════════════
' RunAssemblyRelinkPass  —  Phase 3 of the DrawingCopyMode 4-phase sequence
'
' Declared BEFORE RunDrawingCopyMode — iLogic compiler is single-pass and
' requires a Sub to be declared before the first call to it.
'
' After ALL files are copied (Phase 2 / copy atomic), this pass opens each copied
' .iam/.ipt in the rename map and updates its internal FileDescriptors to point to
' the new filenames in the target folder.
'
' Uses Document.File.ReferencedFileDescriptors — the same file-record API used by
' the drawing pass — so order is not critical for correctness: ReplaceReference
' modifies the stored path string in the file XML directly without needing the
' referenced document to be loaded.  Files are still sorted longest-path-first
' (belt-and-suspenders deepest-first heuristic, consistent with Mode 2 Phase 3).
'
' Content Centre / locked FD (HResult = 0x80070057) → ASMRELINK-SKIP-CC (safe)
'
' Log tokens:
'   ASMRELINK-OK   [file]: ref → ref  (reference replaced)
'   ASMRELINK-SKIP [file]: no matching refs  (file needs no relinking)
'   ASMRELINK-SKIP-CC [file]: ref  (Content Centre FD — not writable, safe)
'   ASMRELINK-SAVE-OK [file]
'   ASMRELINK-FAIL [file]: <reason>
' ═══════════════════════════════════════════════════════════════════════════════
Sub RunAssemblyRelinkPass( _
    oRelinkMap As System.Collections.Generic.Dictionary(Of String, String), _
    sLogFilePath As String, _
    ByRef iRelinkOkOut As Integer, _
    ByRef iRelinkFailOut As Integer, _
    ByRef iRelinkSkipOut As Integer)

    iRelinkOkOut = 0
    iRelinkFailOut = 0
    iRelinkSkipOut = 0

    ' Collect unique new .iam/.ipt paths from the VALUE side of the rename map
    Dim oNewPaths As New System.Collections.Generic.List(Of String)()
    Dim oSeenPaths As New System.Collections.Generic.HashSet(Of String)(StringComparer.OrdinalIgnoreCase)
    For Each kvpRl As System.Collections.Generic.KeyValuePair(Of String, String) In oRelinkMap
        Dim sExtRl As String = System.IO.Path.GetExtension(kvpRl.Value).ToUpper()
        If (sExtRl = ".IAM" OrElse sExtRl = ".IPT") AndAlso Not oSeenPaths.Contains(kvpRl.Value) Then
            If System.IO.File.Exists(kvpRl.Value) Then
                oSeenPaths.Add(kvpRl.Value)
                oNewPaths.Add(kvpRl.Value)
            End If
        End If
    Next

    ' Sort longest-path-first (deepest assemblies first, GA last — consistent with Mode 2 Phase 3)
    oNewPaths.Sort(Function(a, b2) b2.Length.CompareTo(a.Length))

    Try : System.IO.File.AppendAllText(sLogFilePath, "ASMRELINK: " & oNewPaths.Count & " model file(s) queued." & vbCrLf) : Catch : End Try

    For Each sAsmNewPath As String In oNewPaths
        Dim sAsmFn As String = System.IO.Path.GetFileName(sAsmNewPath)
        Dim bOpenedHere As Boolean = False
        Dim oAsmDoc As Document = Nothing

        Try
            oAsmDoc = OpenDocTracked(sAsmNewPath, bOpenedHere)
            If oAsmDoc Is Nothing Then
                Try : System.IO.File.AppendAllText(sLogFilePath, "ASMRELINK-FAIL [" & sAsmFn & "]: could not open" & vbCrLf) : Catch : End Try
                iRelinkFailOut = iRelinkFailOut + 1
                Continue For
            End If

            ' Clear read-only before save
            Try
                Dim oFa As System.IO.FileAttributes = System.IO.File.GetAttributes(sAsmNewPath)
                If (oFa And System.IO.FileAttributes.ReadOnly) = System.IO.FileAttributes.ReadOnly Then
                    System.IO.File.SetAttributes(sAsmNewPath, oFa And Not System.IO.FileAttributes.ReadOnly)
                End If
            Catch : End Try

            ' Suppress iLogic event rules during this pass
            Try : oAsmDoc.iLogicVb.EventRuleManager.DisableEventRules = True : Catch : End Try

            Dim iRepOkAsm As Integer = 0
            Dim iRepFailAsm As Integer = 0
            Try
                For Each oAsmFD As FileDescriptor In oAsmDoc.File.ReferencedFileDescriptors
                    Dim sAsmRefFull As String = ""
                    Try : sAsmRefFull = oAsmFD.FullFileName : Catch : Continue For : End Try
                    If Trim(sAsmRefFull) = "" Then Continue For
                    ' Strip DART tag if present (<DART ...>)
                    If sAsmRefFull.Contains("<") Then
                        sAsmRefFull = sAsmRefFull.Substring(0, sAsmRefFull.IndexOf("<"c)).Trim()
                    End If
                    If Not oRelinkMap.ContainsKey(sAsmRefFull) Then Continue For
                    Dim sAsmNewRef As String = oRelinkMap(sAsmRefFull)
                    If String.Compare(sAsmRefFull, sAsmNewRef, True) = 0 Then Continue For
                    Try
                        oAsmFD.ReplaceReference(sAsmNewRef)
                        iRepOkAsm = iRepOkAsm + 1
                        Try : System.IO.File.AppendAllText(sLogFilePath, "ASMRELINK-OK [" & sAsmFn & "]: " & System.IO.Path.GetFileName(sAsmRefFull) & " -> " & System.IO.Path.GetFileName(sAsmNewRef) & vbCrLf) : Catch : End Try
                    Catch exAsmFD As Exception
                        ' E_INVALIDARG (0x80070057) = Content Centre / locked descriptor — safe skip
                        If exAsmFD.HResult = &H80070057 Then
                            Try : System.IO.File.AppendAllText(sLogFilePath, "ASMRELINK-SKIP-CC [" & sAsmFn & "]: " & System.IO.Path.GetFileName(sAsmRefFull) & vbCrLf) : Catch : End Try
                        Else
                            iRepFailAsm = iRepFailAsm + 1
                            Try : System.IO.File.AppendAllText(sLogFilePath, "ASMRELINK-FAIL [" & sAsmFn & "]: FD " & System.IO.Path.GetFileName(sAsmRefFull) & " — " & exAsmFD.Message & vbCrLf) : Catch : End Try
                        End If
                    End Try
                Next
            Catch exFDLoop As Exception
                iRepFailAsm = iRepFailAsm + 1
                Try : System.IO.File.AppendAllText(sLogFilePath, "ASMRELINK-FAIL [" & sAsmFn & "]: FD loop — " & exFDLoop.Message & vbCrLf) : Catch : End Try
            End Try

            If iRepOkAsm = 0 AndAlso iRepFailAsm = 0 Then
                iRelinkSkipOut = iRelinkSkipOut + 1
                Try : System.IO.File.AppendAllText(sLogFilePath, "ASMRELINK-SKIP [" & sAsmFn & "]: no matching refs" & vbCrLf) : Catch : End Try
            ElseIf iRepFailAsm > 0 Then
                iRelinkFailOut = iRelinkFailOut + 1
            End If

            ' Save if any refs were replaced successfully
            If iRepOkAsm > 0 Then
                Try
                    oAsmDoc.Save2(False)
                    iRelinkOkOut = iRelinkOkOut + 1
                    Try : System.IO.File.AppendAllText(sLogFilePath, "ASMRELINK-SAVE-OK: " & sAsmFn & vbCrLf) : Catch : End Try
                Catch exAsmSave As Exception
                    iRelinkFailOut = iRelinkFailOut + 1
                    Try : System.IO.File.AppendAllText(sLogFilePath, "ASMRELINK-FAIL [" & sAsmFn & "]: save failed — " & exAsmSave.Message & vbCrLf) : Catch : End Try
                End Try
            End If

        Catch exOuter As Exception
            iRelinkFailOut = iRelinkFailOut + 1
            Try : System.IO.File.AppendAllText(sLogFilePath, "ASMRELINK-FAIL [" & sAsmFn & "]: outer — " & exOuter.Message & vbCrLf) : Catch : End Try
        Finally
            If oAsmDoc IsNot Nothing Then
                ' Re-enable event rules before closing
                Try : oAsmDoc.iLogicVb.EventRuleManager.DisableEventRules = False : Catch : End Try
                If bOpenedHere Then
                    Try : oAsmDoc.Close(True) : Catch : End Try
                End If
            End If
        End Try
    Next

End Sub

Sub RunDrawingCopyMode(oDwgDoc As DrawingDocument, Optional oPresetModelRenameMap As System.Collections.Generic.Dictionary(Of String, String) = Nothing)

    Dim sLogFilePath As String = System.Environment.GetFolderPath(System.Environment.SpecialFolder.Desktop) & "\DrawingCopyMode_Log_" & DateTime.Now.ToString("yyyy-MM-dd_HHmmss") & ".txt"
    Try
        System.IO.File.WriteAllText(sLogFilePath, "DRAWING COPY MODE" & vbCrLf & "Started: " & DateTime.Now.ToString() & vbCrLf & "Drawing: " & oDwgDoc.FullFileName & vbCrLf)
    Catch
    End Try

    Dim bOrigSilent As Boolean = ThisApplication.SilentOperation
    ' Suppress iLogic event-driven rules (e.g. "Working Drawing Stamp") for the entire
    ' RunDrawingCopyMode run — sibling drawings opened in Phase 1 scan fire event rules
    ' before SilentOperation has any effect. Restored at every exit point below.
    Dim bOrigEventRules As Boolean = False
    Try : bOrigEventRules = ThisApplication.iLogicVb.EventRuleManager.DisableEventRules : Catch : End Try
    Try : ThisApplication.iLogicVb.EventRuleManager.DisableEventRules = True : Catch : End Try
    ThisApplication.SilentOperation = False  ' keep dialogs visible

    ' ── 1. Scan ALL drawings in folder for model references ────────────
    ' oAllDwgRefs : dwgFullPath -> List(Of modelFullPath)  (all .iam/.ipt refs per drawing)
    ' oAllModelPaths : unique model full paths across all drawings (for folder picker seed)
    ' Active drawing is scanned first (already open); siblings opened silently then closed.
    Dim sDwgFolder As String = System.IO.Path.GetDirectoryName(oDwgDoc.FullFileName)
    Dim sActiveDwgPath As String = oDwgDoc.FullFileName
    Dim oAllDwgPaths As New System.Collections.Generic.List(Of String)
    oAllDwgPaths.Add(sActiveDwgPath)
    Try
        For Each sDwgFile As String In System.IO.Directory.GetFiles(sDwgFolder, "*.dwg")
            If String.Compare(sDwgFile, sActiveDwgPath, True) <> 0 Then
                oAllDwgPaths.Add(sDwgFile)
            End If
        Next
    Catch
    End Try

    Dim oAllDwgRefs As New System.Collections.Generic.Dictionary(Of String, System.Collections.Generic.List(Of String))(StringComparer.OrdinalIgnoreCase)
    Dim oAllModelPaths As New System.Collections.Generic.List(Of String)
    ' TB1_EN5_TYPE custom iProperty description per drawing (optional — empty string if absent)
    Dim oDwgDescriptions As New System.Collections.Generic.Dictionary(Of String, String)(StringComparer.OrdinalIgnoreCase)

    ' Helper: add model refs from a DrawingDocument into oAllDwgRefs
    ' Uses ReferencedDocumentDescriptors (not ReferencedDocuments) so that
    ' DART SHUT references — model refs present in the drawing but in an
    ' unloaded/shutdown state — are included. ReferencedDocuments silently
    ' omits DART SHUT refs; descriptors return them all.
    Dim oScanRefs As New System.Collections.Generic.List(Of String)
    Try
        For Each oDesc As Object In oDwgDoc.ReferencedDocumentDescriptors
            Dim sRefPath As String = ""
            Try : sRefPath = oDesc.FullDocumentName : Catch : Continue For : End Try
            ' Strip any DART state tag, e.g. "path.iam<DART SHUT>" → "path.iam"
            Dim iAngle As Integer = sRefPath.IndexOf("<"c)
            If iAngle > 0 Then
                Dim sDartTag As String = sRefPath.Substring(iAngle)
                sRefPath = sRefPath.Substring(0, iAngle)
                Try : System.IO.File.AppendAllText(sLogFilePath, "DART-REF: " & System.IO.Path.GetFileName(sRefPath) & " " & sDartTag & vbCrLf) : Catch : End Try
            End If
            If Trim(sRefPath) = "" Then Continue For
            Dim sExt As String = System.IO.Path.GetExtension(sRefPath).ToUpper()
            If sExt = ".IAM" OrElse sExt = ".IPT" Then
                If Not oScanRefs.Contains(sRefPath) Then oScanRefs.Add(sRefPath)
                If Not oAllModelPaths.Contains(sRefPath) Then oAllModelPaths.Add(sRefPath)
            End If
        Next
    Catch exRef As Exception
        ' ReferencedDocumentDescriptors failed — fall back to ReferencedDocuments
        Try : System.IO.File.AppendAllText(sLogFilePath, "SCAN-FALLBACK: descriptors failed (" & exRef.Message & ") — using ReferencedDocuments" & vbCrLf) : Catch : End Try
        Try
            For Each oRef As Document In oDwgDoc.ReferencedDocuments
                Dim sRefPath As String = ""
                Try : sRefPath = oRef.FullDocumentName : Catch : Continue For : End Try
                If Trim(sRefPath) = "" Then Continue For
                Dim sExt As String = System.IO.Path.GetExtension(sRefPath).ToUpper()
                If sExt = ".IAM" OrElse sExt = ".IPT" Then
                    If Not oScanRefs.Contains(sRefPath) Then oScanRefs.Add(sRefPath)
                    If Not oAllModelPaths.Contains(sRefPath) Then oAllModelPaths.Add(sRefPath)
                End If
            Next
        Catch exRef2 As Exception
            MessageBox.Show("Could not read active drawing references: " & exRef2.Message, "Drawing Copy Mode Error")
            Try : ThisApplication.iLogicVb.EventRuleManager.DisableEventRules = bOrigEventRules : Catch : End Try
            ThisApplication.SilentOperation = bOrigSilent
            Return
        End Try
    End Try
    oAllDwgRefs(sActiveDwgPath) = oScanRefs
    ' Read TB1_EN5_TYPE description from active drawing
    Dim sActiveDesc As String = ""
    Try : sActiveDesc = CStr(oDwgDoc.PropertySets.Item("Inventor User Defined Properties").Item("5DRAWING TYPE").Value) : Catch : End Try
    oDwgDescriptions(sActiveDwgPath) = Trim(sActiveDesc)
    Try : System.IO.File.AppendAllText(sLogFilePath, "Found " & oScanRefs.Count & " model ref(s) in active drawing." & vbCrLf) : Catch : End Try

    ' ── GA DRAWING LAUNCH GUARD ────────────────────────────────────────────
    ' The rule must be launched from the GA drawing — the drawing that directly
    ' views the top-level assembly (.iam). This is always the first drawing
    ' sequentially (e.g. 000001.dwg). If the active drawing has no .iam ref,
    ' stop immediately rather than silently proceeding on wrong assumptions.
    Dim bHasIamRef As Boolean = False
    For Each sChkRef As String In oScanRefs
        If String.Compare(System.IO.Path.GetExtension(sChkRef), ".iam", True) = 0 Then
            bHasIamRef = True : Exit For
        End If
    Next
    If Not bHasIamRef Then
        Dim sGuardMsg As String = "No assembly (.iam) reference found in the active drawing." & vbCrLf & vbCrLf & _
            "Please launch this rule from the GA drawing — the drawing that" & vbCrLf & _
            "views the top-level assembly (usually the first drawing, e.g. 000001.dwg)." & vbCrLf & vbCrLf & _
            "Active drawing: " & System.IO.Path.GetFileName(sActiveDwgPath)
        MessageBox.Show(sGuardMsg, "Drawing Copy Mode — Wrong Starting Drawing", MessageBoxButtons.OK, MessageBoxIcon.Warning)
        Try : System.IO.File.AppendAllText(sLogFilePath, "GUARD-FAIL: no .iam ref in active drawing — user directed to GA drawing." & vbCrLf) : Catch : End Try
        Try : ThisApplication.iLogicVb.EventRuleManager.DisableEventRules = bOrigEventRules : Catch : End Try
        ThisApplication.SilentOperation = bOrigSilent
        Return
    End If

    ' ── PRINCIPAL GA SELECTION ──────────────────────────────────────────────
    ' Collect all .iam refs from the active drawing scan.
    ' - Exactly one  → assumed to be the principal GA, no dialog needed.
    ' - Two or more  → user nominates the principal GA via radio-button dialog.
    '   Secondary .iam refs (reference models placed for context) are removed
    '   from oScanRefs so the downstream tree walk ignores them, but they will
    '   still be copied into the model folder with their existing names and their
    '   drawing references updated.
    Dim oIamRefsInDrawing As New System.Collections.Generic.List(Of String)
    For Each sChkIam As String In oScanRefs
        If String.Compare(System.IO.Path.GetExtension(sChkIam), ".iam", True) = 0 Then
            oIamRefsInDrawing.Add(sChkIam)
        End If
    Next

    Dim sSelectedGaPath As String = ""
    If oIamRefsInDrawing.Count = 1 Then
        sSelectedGaPath = oIamRefsInDrawing(0)
        Try : System.IO.File.AppendAllText(sLogFilePath, "GA-PRINCIPAL: single .iam in drawing — assumed GA: " & System.IO.Path.GetFileName(sSelectedGaPath) & vbCrLf) : Catch : End Try
    Else
        ' Multiple .iam refs — user must nominate the principal GA
        sSelectedGaPath = ShowGaSelectionDialog(oIamRefsInDrawing, sActiveDwgPath)
        If Trim(sSelectedGaPath) = "" Then
            ' User cancelled without selecting
            Try : System.IO.File.AppendAllText(sLogFilePath, "GA-CANCEL: user cancelled principal GA selection — rule aborted." & vbCrLf) : Catch : End Try
            Try : ThisApplication.iLogicVb.EventRuleManager.DisableEventRules = bOrigEventRules : Catch : End Try
            ThisApplication.SilentOperation = bOrigSilent
            Return
        End If
        Try : System.IO.File.AppendAllText(sLogFilePath, "GA-PRINCIPAL: user nominated " & System.IO.Path.GetFileName(sSelectedGaPath) & " as principal GA (" & oIamRefsInDrawing.Count & " .iam refs in drawing)" & vbCrLf) : Catch : End Try
        ' Strip secondary .iam refs from oScanRefs — they are not part of the GA tree.
        ' The drawing ref-update pass will still re-point them to their new location.
        For Each sNonGa As String In oIamRefsInDrawing
            If String.Compare(sNonGa, sSelectedGaPath, True) <> 0 Then
                oScanRefs.Remove(sNonGa)
                Try : System.IO.File.AppendAllText(sLogFilePath, "GA-SECONDARY: excluded from tree walk (copied as-is): " & System.IO.Path.GetFileName(sNonGa) & vbCrLf) : Catch : End Try
            End If
        Next
    End If

    ' ── PRE-RULE TREE GRAB ─────────────────────────────────────────────────
    ' Captures the full GA assembly tree before any changes are made.
    ' Written to sDwgFolder (permanent record) and Desktop (quick access).
    ' Compare against POST tree to see exactly what the rule changed.
    Dim sRunStamp As String = DateTime.Now.ToString("yyyy-MM-dd_HHmmss")
    Dim sPreTreeDesktop As String = System.Environment.GetFolderPath(System.Environment.SpecialFolder.Desktop) & "\PRE_Tree_" & sRunStamp & ".txt"
    Dim sPreTreeDwgFolder As String = System.IO.Path.Combine(sDwgFolder, "PRE_Tree_" & sRunStamp & ".txt")
    Try
        ' Find the GA assembly: scan open Documents first (safe, no IO, no resolve).
        ' This works even when the active drawing is a title sheet with 0 model refs.
        ' Fallback 1: oScanRefs (active drawing refs). Fallback 2: any open .iam in same folder.
        Dim sPreGaPath As String = ""
        ' -- Primary: scan ThisApplication.Documents for an open .iam in same project tree --
        Dim sDwgParent As String = System.IO.Path.GetDirectoryName(sDwgFolder.TrimEnd(System.IO.Path.DirectorySeparatorChar))
        ' Single pass over open documents — cached for GA-open check below (Fix #7)
        Dim oPreTreeDocCache As New System.Collections.Generic.Dictionary(Of String, Document)(StringComparer.OrdinalIgnoreCase)
        Dim oOpenIamCandidates As New System.Collections.Generic.List(Of String)
        Try
            For Each oOpenD As Document In ThisApplication.Documents
                Dim sOpenPath As String = ""
                Try : sOpenPath = oOpenD.FullFileName : Catch : Continue For : End Try
                If Trim(sOpenPath) <> "" Then oPreTreeDocCache(sOpenPath) = oOpenD  ' cache for reuse
                If String.Compare(System.IO.Path.GetExtension(sOpenPath), ".iam", True) = 0 Then
                    ' Accept .iam files in the same folder or any sibling/child of the project parent
                    Dim sOpenFolder As String = System.IO.Path.GetDirectoryName(sOpenPath)
                    If sOpenFolder.StartsWith(sDwgParent, StringComparison.OrdinalIgnoreCase) Then
                        oOpenIamCandidates.Add(sOpenPath)
                    End If
                End If
            Next
        Catch : End Try
        If oOpenIamCandidates.Count = 1 Then
            sPreGaPath = oOpenIamCandidates(0)
            Try : System.IO.File.AppendAllText(sLogFilePath, "PRE-TREE: GA found via open Documents → " & System.IO.Path.GetFileName(sPreGaPath) & vbCrLf) : Catch : End Try
        ElseIf oOpenIamCandidates.Count > 1 Then
            ' Multiple .iam open — pick the one in the same folder as drawings, or first one
            sPreGaPath = oOpenIamCandidates(0)
            For Each sCand As String In oOpenIamCandidates
                If System.IO.Path.GetDirectoryName(sCand).Equals(sDwgFolder, StringComparison.OrdinalIgnoreCase) Then
                    sPreGaPath = sCand : Exit For
                End If
            Next
            Try : System.IO.File.AppendAllText(sLogFilePath, "PRE-TREE: multiple .iam open — using " & System.IO.Path.GetFileName(sPreGaPath) & " (" & oOpenIamCandidates.Count & " candidates)" & vbCrLf) : Catch : End Try
        End If
        ' -- Fallback: oScanRefs (active drawing model refs) --
        If Trim(sPreGaPath) = "" Then
            For Each sScanRef As String In oScanRefs
                If String.Compare(System.IO.Path.GetExtension(sScanRef), ".iam", True) = 0 Then
                    sPreGaPath = sScanRef
                    Try : System.IO.File.AppendAllText(sLogFilePath, "PRE-TREE: GA found via active drawing ref → " & System.IO.Path.GetFileName(sPreGaPath) & vbCrLf) : Catch : End Try
                    Exit For
                End If
            Next
        End If
        If Trim(sPreGaPath) <> "" AndAlso System.IO.File.Exists(sPreGaPath) Then
            Dim sPreHeader As String = "PRE-RULE ASSEMBLY TREE SNAPSHOT" & vbCrLf & _
                "Generated: " & DateTime.Now.ToString() & vbCrLf & _
                "Assembly: " & sPreGaPath & vbCrLf & _
                New String("="c, 120) & vbCrLf & vbCrLf
            System.IO.File.WriteAllText(sPreTreeDesktop, sPreHeader)
            System.IO.File.WriteAllText(sPreTreeDwgFolder, sPreHeader)
            Dim oPreGaDoc As AssemblyDocument = Nothing
            Dim bPreWasOpen As Boolean = False
            Try
                ' Reuse cached open-doc scan — no second Documents enumeration (Fix #7)
                Dim oCachedPre As Document = Nothing
                If oPreTreeDocCache.TryGetValue(sPreGaPath, oCachedPre) Then
                    oPreGaDoc = TryCast(oCachedPre, AssemblyDocument)
                    bPreWasOpen = True
                End If
                If oPreGaDoc Is Nothing Then
                    oPreGaDoc = TryCast(ThisApplication.Documents.Open(sPreGaPath, False), AssemblyDocument)
                End If
            Catch : End Try
            If oPreGaDoc IsNot Nothing Then
                Dim iPreCount As Integer = 0
                WalkTreeToLog(oPreGaDoc.ComponentDefinition.Occurrences, 0, sPreTreeDesktop, iPreCount)
                WalkTreeToLog(oPreGaDoc.ComponentDefinition.Occurrences, 0, sPreTreeDwgFolder, iPreCount)
                Dim sPreFooter As String = vbCrLf & New String("="c, 120) & vbCrLf & "Total occurrences listed: " & iPreCount & vbCrLf
                System.IO.File.AppendAllText(sPreTreeDesktop, sPreFooter)
                System.IO.File.AppendAllText(sPreTreeDwgFolder, sPreFooter)
                If Not bPreWasOpen Then Try : oPreGaDoc.Close(False) : Catch : End Try
                Try : System.IO.File.AppendAllText(sLogFilePath, "PRE-TREE: " & iPreCount & " occurrence(s) captured → " & System.IO.Path.GetFileName(sPreTreeDwgFolder) & vbCrLf) : Catch : End Try
            End If
        Else
            Try : System.IO.File.AppendAllText(sLogFilePath, "PRE-TREE: no GA .iam found in active drawing refs — skipped" & vbCrLf) : Catch : End Try
        End If
    Catch exPre As Exception
        Try : System.IO.File.AppendAllText(sLogFilePath, "PRE-TREE-FAIL: " & exPre.Message & vbCrLf) : Catch : End Try
    End Try

    ' Scan sibling drawings silently
    ThisApplication.SilentOperation = True
    Dim iSibIdx As Integer
    For iSibIdx = 1 To oAllDwgPaths.Count - 1
        Dim sSibPath As String = oAllDwgPaths(iSibIdx)
        Dim oSibDwg As DrawingDocument = Nothing
        Dim bOpenedSib As Boolean = False
        Try : oSibDwg = TryCast(ThisApplication.Documents.ItemByName(sSibPath), DrawingDocument) : Catch : End Try
        If oSibDwg Is Nothing Then
            Try
                oSibDwg = TryCast(ThisApplication.Documents.Open(sSibPath, False), DrawingDocument)
                bOpenedSib = True
            Catch exSibOpen As Exception
                Try : System.IO.File.AppendAllText(sLogFilePath, "SCAN-OPEN-FAIL: " & System.IO.Path.GetFileName(sSibPath) & " : " & exSibOpen.Message & vbCrLf) : Catch : End Try
                oAllDwgRefs(sSibPath) = New System.Collections.Generic.List(Of String)
                Continue For
            End Try
        End If
        Dim oSibRefs As New System.Collections.Generic.List(Of String)
        Try
            ' Use ReferencedDocumentDescriptors to catch DART SHUT refs
            For Each oSibDesc As Object In oSibDwg.ReferencedDocumentDescriptors
                Dim sSibRefPath As String = ""
                Try : sSibRefPath = oSibDesc.FullDocumentName : Catch : Continue For : End Try
                Dim iSibAngle As Integer = sSibRefPath.IndexOf("<"c)
                If iSibAngle > 0 Then sSibRefPath = sSibRefPath.Substring(0, iSibAngle)
                If Trim(sSibRefPath) = "" Then Continue For
                Dim sSibExt As String = System.IO.Path.GetExtension(sSibRefPath).ToUpper()
                If sSibExt = ".IAM" OrElse sSibExt = ".IPT" Then
                    If Not oSibRefs.Contains(sSibRefPath) Then oSibRefs.Add(sSibRefPath)
                    If Not oAllModelPaths.Contains(sSibRefPath) Then oAllModelPaths.Add(sSibRefPath)
                End If
            Next
        Catch
            ' Fallback to ReferencedDocuments if descriptors unavailable
            Try
                For Each oSibRef As Document In oSibDwg.ReferencedDocuments
                    Dim sSibRefPath As String = ""
                    Try : sSibRefPath = oSibRef.FullDocumentName : Catch : Continue For : End Try
                    If Trim(sSibRefPath) = "" Then Continue For
                    Dim sSibExt As String = System.IO.Path.GetExtension(sSibRefPath).ToUpper()
                    If sSibExt = ".IAM" OrElse sSibExt = ".IPT" Then
                        If Not oSibRefs.Contains(sSibRefPath) Then oSibRefs.Add(sSibRefPath)
                        If Not oAllModelPaths.Contains(sSibRefPath) Then oAllModelPaths.Add(sSibRefPath)
                    End If
                Next
            Catch
            End Try
        End Try
        oAllDwgRefs(sSibPath) = oSibRefs
        ' Read TB1_EN5_TYPE description from sibling drawing
        Dim sSibDesc As String = ""
        Try : sSibDesc = CStr(oSibDwg.PropertySets.Item("Inventor User Defined Properties").Item("5DRAWING TYPE").Value) : Catch : End Try
        oDwgDescriptions(sSibPath) = Trim(sSibDesc)
        Try : System.IO.File.AppendAllText(sLogFilePath, "SCAN-OK: " & System.IO.Path.GetFileName(sSibPath) & " (" & oSibRefs.Count & " model ref(s))" & vbCrLf) : Catch : End Try
        If bOpenedSib Then
            Try : oSibDwg.Close(True) : Catch : End Try
        End If
    Next
    ThisApplication.SilentOperation = False

    If oAllModelPaths.Count = 0 Then
        MessageBox.Show("No .iam or .ipt model references found in any drawing in this folder.", "Drawing Copy Mode")
        Try : ThisApplication.iLogicVb.EventRuleManager.DisableEventRules = bOrigEventRules : Catch : End Try
        ThisApplication.SilentOperation = bOrigSilent
        Return
    End If

    Try : System.IO.File.AppendAllText(sLogFilePath, "Total unique model refs across all drawings: " & oAllModelPaths.Count & vbCrLf) : Catch : End Try

    ' ── DRAWING REFS REPORT ────────────────────────────────────────────────
    ' Always written regardless of mode. Shows every drawing and its resolved
    ' model refs. Rename-map match status is appended at end of run.
    Dim sDwgRefsDesktop As String = System.Environment.GetFolderPath(System.Environment.SpecialFolder.Desktop) & "\DrawingRefs_" & sRunStamp & ".txt"
    Dim sDwgRefsDwgFolder As String = System.IO.Path.Combine(sDwgFolder, "DrawingRefs_" & sRunStamp & ".txt")
    Try
        Dim sbDwgRefs As New System.Text.StringBuilder()
        sbDwgRefs.AppendLine("DRAWING REFS REPORT")
        sbDwgRefs.AppendLine("Generated: " & DateTime.Now.ToString())
        sbDwgRefs.AppendLine("Drawings folder: " & sDwgFolder)
        sbDwgRefs.AppendLine(New String("="c, 120))
        sbDwgRefs.AppendLine()
        For Each oKvpDwg As System.Collections.Generic.KeyValuePair(Of String, System.Collections.Generic.List(Of String)) In oAllDwgRefs
            sbDwgRefs.AppendLine("DWG: " & System.IO.Path.GetFileName(oKvpDwg.Key))
            If oKvpDwg.Value.Count = 0 Then
                sbDwgRefs.AppendLine("   (no model refs resolved)")
            Else
                For Each sRefItem As String In oKvpDwg.Value
                    sbDwgRefs.AppendLine("   REF: " & sRefItem)
                Next
            End If
            sbDwgRefs.AppendLine()
        Next
        sbDwgRefs.AppendLine(New String("="c, 120))
        sbDwgRefs.AppendLine("NOTE: rename-map match status appended at end of run.")
        System.IO.File.WriteAllText(sDwgRefsDesktop, sbDwgRefs.ToString())
        System.IO.File.WriteAllText(sDwgRefsDwgFolder, sbDwgRefs.ToString())
        Try : System.IO.File.AppendAllText(sLogFilePath, "DRAWING-REFS: report written → " & System.IO.Path.GetFileName(sDwgRefsDwgFolder) & vbCrLf) : Catch : End Try
    Catch exDwgRefs As Exception
        Try : System.IO.File.AppendAllText(sLogFilePath, "DRAWING-REFS-FAIL: " & exDwgRefs.Message & vbCrLf) : Catch : End Try
    End Try

    ' ── 2a. Target folder picker ────────────────────────────────────────
    Dim sFirstModelFolder As String = System.IO.Path.GetDirectoryName(oAllModelPaths(0))

    Dim oFbd As New FolderBrowserDialog()
    oFbd.Description = "DRAWING COPY MODE — Select folder for new model copies"
    Dim sSeedFolder As String = If(System.IO.Directory.Exists(sFirstModelFolder), sFirstModelFolder, sDwgFolder)
    If System.IO.Directory.Exists(sSeedFolder) Then oFbd.SelectedPath = sSeedFolder
    If oFbd.ShowDialog() <> DialogResult.OK Then
        MessageBox.Show("Cancelled — no changes made.", "Drawing Copy Mode")
        Try : ThisApplication.iLogicVb.EventRuleManager.DisableEventRules = bOrigEventRules : Catch : End Try
        ThisApplication.SilentOperation = bOrigSilent
        Return
    End If
    Dim sTargetFolder As String = oFbd.SelectedPath
    If Not System.IO.Directory.Exists(sTargetFolder) Then
        Try
            System.IO.Directory.CreateDirectory(sTargetFolder)
        Catch exMk As Exception
            MessageBox.Show("Could not create target folder: " & exMk.Message, "Drawing Copy Mode")
            Try : ThisApplication.iLogicVb.EventRuleManager.DisableEventRules = bOrigEventRules : Catch : End Try
            ThisApplication.SilentOperation = bOrigSilent
            Return
        End Try
    End If
    Try : System.IO.File.AppendAllText(sLogFilePath, "Target folder: " & sTargetFolder & vbCrLf) : Catch : End Try

    ' ══════════════════════════════════════════════════════════════════════
    ' RUN LOG — _CleanSweeper_RunLog.txt
    ' Append-only per-run record written to sTargetFolder.
    ' Pass 1 [ORIGIN] block captures original GA tree and drawing refs —
    ' never overwritten on subsequent runs. All passes are cumulative so
    ' any prior state can be recovered from the pass history.
    ' ══════════════════════════════════════════════════════════════════════
    Dim sRunLogPath As String = System.IO.Path.Combine(sTargetFolder, "_CleanSweeper_RunLog.txt")
    Dim iRunPass As Integer = 1
    Dim bIsOriginPass As Boolean = False
    ' Determine pass number by counting existing pass headers
    Try
        If System.IO.File.Exists(sRunLogPath) Then
            Dim sExistLog As String = System.IO.File.ReadAllText(sRunLogPath)
            Dim iHeaderPos As Integer = 0
            Dim iFoundCount As Integer = 0
            Do
                Dim iNext As Integer = sExistLog.IndexOf("PASS ", iHeaderPos, StringComparison.OrdinalIgnoreCase)
                If iNext < 0 Then Exit Do
                iFoundCount += 1
                iHeaderPos = iNext + 5
            Loop
            If iFoundCount > 0 Then iRunPass = iFoundCount + 1
        End If
    Catch : End Try
    bIsOriginPass = (iRunPass = 1)
    Dim sPassLabel As String = "PASS " & iRunPass & " — " & sRunStamp & If(bIsOriginPass, "  [ORIGIN]", "")
    Try
        Dim sbPassHeader As New System.Text.StringBuilder()
        sbPassHeader.AppendLine()
        sbPassHeader.AppendLine(New String("="c, 53))
        sbPassHeader.AppendLine(sPassLabel)
        sbPassHeader.AppendLine(New String("="c, 53))
        sbPassHeader.AppendLine("drawing_folder = " & sDwgFolder)
        sbPassHeader.AppendLine("target_folder = " & sTargetFolder)
        sbPassHeader.AppendLine("started_by = " & System.Environment.UserName)
        sbPassHeader.AppendLine()
        System.IO.File.AppendAllText(sRunLogPath, sbPassHeader.ToString())
        Try : System.IO.File.AppendAllText(sLogFilePath, "RUN-LOG: pass " & iRunPass & " opened → " & System.IO.Path.GetFileName(sRunLogPath) & vbCrLf) : Catch : End Try
    Catch exRunLog As Exception
        Try : System.IO.File.AppendAllText(sLogFilePath, "RUN-LOG-FAIL: " & exRunLog.Message & vbCrLf) : Catch : End Try
    End Try

    ' ── 2b. Re-run detection: look for existing copy in target folder ───
    ' Seed new prefix from the DRAWING's own filename — it already carries the
    ' new project prefix (e.g. PJ00205-GTA-3450-6-000001.dwg → PJ00205).
    Dim sNewPrefix As String = ""
    Dim sDwgBase As String = System.IO.Path.GetFileNameWithoutExtension(oDwgDoc.FullFileName)
    Dim iDwgDash As Integer = sDwgBase.IndexOf("-"c)
    If iDwgDash > 0 Then sNewPrefix = sDwgBase.Substring(0, iDwgDash)

    Dim bPrefixLocked As Boolean = False
    Dim sFirstModelBase As String = System.IO.Path.GetFileNameWithoutExtension(oAllModelPaths(0))
    Dim sFirstModelExt As String = System.IO.Path.GetExtension(oAllModelPaths(0))
    Dim iFirstModelDash As Integer = sFirstModelBase.IndexOf("-"c)
    If iFirstModelDash > 0 Then
        Dim sFirstModelSuffix As String = sFirstModelBase.Substring(iFirstModelDash) & sFirstModelExt
        Dim sFirstModelSuffixUp As String = sFirstModelSuffix.ToUpper()
        Try
            For Each sExisting As String In System.IO.Directory.GetFiles(sTargetFolder, "*" & sFirstModelExt)
                Dim sExBase As String = System.IO.Path.GetFileName(sExisting)
                If sExBase.ToUpper().EndsWith(sFirstModelSuffixUp) Then
                    Dim iExDash As Integer = sExBase.IndexOf("-"c)
                    If iExDash > 0 Then
                        Dim sDetected As String = sExBase.Substring(0, iExDash)
                        If Trim(sDetected) <> "" Then
                            sNewPrefix = sDetected
                            bPrefixLocked = True
                        End If
                    End If
                    Exit For
                End If
            Next
        Catch
        End Try
    End If

    ' ── 2c. Prefix config form ──────────────────────────────────────────
    Dim oOldPrefix As String = ""
    If iFirstModelDash > 0 Then oOldPrefix = sFirstModelBase.Substring(0, iFirstModelDash)

    Dim oCfgForm As New System.Windows.Forms.Form()
    oCfgForm.Text = "Drawing Copy Mode — New Project Prefix"
    oCfgForm.Width = 480
    oCfgForm.Height = 200
    oCfgForm.FormBorderStyle = System.Windows.Forms.FormBorderStyle.FixedDialog
    oCfgForm.MaximizeBox = False
    oCfgForm.StartPosition = System.Windows.Forms.FormStartPosition.CenterScreen

    Dim oCfgLbl As New System.Windows.Forms.Label()
    oCfgLbl.Text = "Current prefix detected from models:  " & oOldPrefix
    oCfgLbl.Left = 12 : oCfgLbl.Top = 14 : oCfgLbl.Width = 440 : oCfgLbl.Height = 18
    oCfgForm.Controls.Add(oCfgLbl)

    Dim oCfgLbl2 As New System.Windows.Forms.Label()
    If bPrefixLocked Then
        oCfgLbl2.Text = "New project prefix  [LOCKED — existing copy detected in target folder]:"
    Else
        oCfgLbl2.Text = "New project prefix (e.g. PJ00205):"
    End If
    oCfgLbl2.Left = 12 : oCfgLbl2.Top = 44 : oCfgLbl2.Width = 440 : oCfgLbl2.Height = 18
    oCfgForm.Controls.Add(oCfgLbl2)

    Dim oCfgTxt As New System.Windows.Forms.TextBox()
    oCfgTxt.Left = 12 : oCfgTxt.Top = 66 : oCfgTxt.Width = 200
    oCfgTxt.Text = If(Trim(sNewPrefix) <> "", sNewPrefix, "")
    oCfgTxt.Enabled = Not bPrefixLocked
    oCfgForm.Controls.Add(oCfgTxt)

    Dim oCfgOk As New System.Windows.Forms.Button()
    oCfgOk.Text = "Continue" : oCfgOk.Left = 12 : oCfgOk.Top = 104 : oCfgOk.Width = 90 : oCfgOk.Height = 28
    oCfgOk.DialogResult = System.Windows.Forms.DialogResult.OK
    oCfgForm.Controls.Add(oCfgOk)
    oCfgForm.AcceptButton = oCfgOk

    Dim oCfgCancel As New System.Windows.Forms.Button()
    oCfgCancel.Text = "Cancel" : oCfgCancel.Left = 110 : oCfgCancel.Top = 104 : oCfgCancel.Width = 80 : oCfgCancel.Height = 28
    oCfgCancel.DialogResult = System.Windows.Forms.DialogResult.Cancel
    oCfgForm.Controls.Add(oCfgCancel)
    oCfgForm.CancelButton = oCfgCancel

    If oCfgForm.ShowDialog() <> System.Windows.Forms.DialogResult.OK Then
        MessageBox.Show("Cancelled — no changes made.", "Drawing Copy Mode")
        Try : ThisApplication.iLogicVb.EventRuleManager.DisableEventRules = bOrigEventRules : Catch : End Try
        ThisApplication.SilentOperation = bOrigSilent
        Return
    End If
    sNewPrefix = Trim(oCfgTxt.Text)
    If sNewPrefix = "" Then
        MessageBox.Show("New prefix cannot be empty.", "Drawing Copy Mode")
        Try : ThisApplication.iLogicVb.EventRuleManager.DisableEventRules = bOrigEventRules : Catch : End Try
        ThisApplication.SilentOperation = bOrigSilent
        Return
    End If
    Try : System.IO.File.AppendAllText(sLogFilePath, "Old prefix: " & oOldPrefix & "  New prefix: " & sNewPrefix & vbCrLf) : Catch : End Try

    ' ── 3. Build Phase0Data for the rename form — one entry per drawing ──
    ' Format: List(Of Object()) where each entry = {sDwgBasename As String, List(Of sModelBasename_noExt)}
    ' Only drawings that have at least one model ref are included.
    ' oBasenameToFullPath: basename_no_ext -> full original path (for building copy map after form)
    Dim oBasenameToFullPath As New System.Collections.Generic.Dictionary(Of String, String)(StringComparer.OrdinalIgnoreCase)
    Dim oPhase0Data As New System.Collections.Generic.List(Of Object())
    Dim iP0Idx As Integer
    For iP0Idx = 0 To oAllDwgPaths.Count - 1
        Dim sP0DwgPath As String = oAllDwgPaths(iP0Idx)
        If Not oAllDwgRefs.ContainsKey(sP0DwgPath) Then Continue For
        Dim oP0Refs As System.Collections.Generic.List(Of String) = oAllDwgRefs(sP0DwgPath)
        If oP0Refs.Count = 0 Then Continue For
        Dim sP0DwgBase As String = System.IO.Path.GetFileName(sP0DwgPath)
        Dim oP0ModelList As New System.Collections.Generic.List(Of String)
        Dim iP0RefIdx As Integer
        For iP0RefIdx = 0 To oP0Refs.Count - 1
            Dim sP0Ref As String = oP0Refs(iP0RefIdx)
            Dim sP0Base As String = System.IO.Path.GetFileNameWithoutExtension(sP0Ref)
            If Not oP0ModelList.Contains(sP0Base) Then oP0ModelList.Add(sP0Base)
            oBasenameToFullPath(sP0Base) = sP0Ref
        Next
        Dim sP0Desc As String = If(oDwgDescriptions.ContainsKey(sP0DwgPath), oDwgDescriptions(sP0DwgPath), "")
        oPhase0Data.Add(New Object() {sP0DwgBase, oP0ModelList, sP0Desc})
    Next

    ' ── 3b. Show the existing Drawing Model Renames form ───────────────
    ' oChoice.sReplace is already set to sNewPrefix so the form pre-fills correctly.
    Dim oFormChoice As New RenameModeChoice()
    oFormChoice.sReplace = sNewPrefix
    oFormChoice.bPrefixLocked = bPrefixLocked

    ' ── PHASE A: Pre-compute exact old→new pairs from drawing scan ─────────
    ' Applies prefix swap to every file the active drawing directly references
    ' (GA + its direct sub-assemblies and parts). Pre-seeds oExplicitModelRenameMap
    ' so the rename form shows exact filename pairs rather than blank rows.
    ' Handles JC assemblies (PJ00193_JCxxxxxx → PJ00205-JCxxxxxx) and other
    ' underscore-separated names that the generic prefix logic misses.
    ' The caller's oPresetModelRenameMap wins if the same key appears in both
    ' (applied in the block immediately below this one).
    If oOldPrefix <> "" AndAlso sNewPrefix <> "" Then
        Dim oPhaseAPairs As New System.Collections.Generic.Dictionary(Of String, String)(StringComparer.OrdinalIgnoreCase)
        Dim sPhaseARef As String
        For Each sPhaseARef In oScanRefs
            Dim sPhaseAOld As String = System.IO.Path.GetFileNameWithoutExtension(sPhaseARef)
            If sPhaseAOld = "" Then Continue For
            Dim sPhaseANew As String = sPhaseAOld
            ' Dash-separated: PJ00193-GTA-3460-10-...  →  PJ00205-GTA-3460-10-...
            If sPhaseANew.StartsWith(oOldPrefix & "-", StringComparison.OrdinalIgnoreCase) Then
                sPhaseANew = sNewPrefix & sPhaseANew.Substring(oOldPrefix.Length)
            ' Underscore-separated (JC / Bolted Connection assemblies):
            ' PJ00193_JC002266  →  PJ00205-JC002266  (underscore becomes dash)
            ElseIf sPhaseANew.StartsWith(oOldPrefix & "_", StringComparison.OrdinalIgnoreCase) Then
                sPhaseANew = sNewPrefix & "-" & sPhaseANew.Substring(oOldPrefix.Length + 1)
            End If
            ' Only register when name actually changes
            If String.Compare(sPhaseANew, sPhaseAOld, True) <> 0 Then
                oPhaseAPairs(sPhaseAOld) = sPhaseANew
            End If
        Next
        If oPhaseAPairs.Count > 0 Then
            Try : System.IO.File.AppendAllText(sLogFilePath, "PHASE-A: pre-computed " & oPhaseAPairs.Count & " exact old→new pair(s) from drawing scan:" & vbCrLf) : Catch : End Try
            Dim kvpA As System.Collections.Generic.KeyValuePair(Of String, String)
            For Each kvpA In oPhaseAPairs
                Try : System.IO.File.AppendAllText(sLogFilePath, "  " & kvpA.Key & " → " & kvpA.Value & vbCrLf) : Catch : End Try
                ' Seed the form — caller preset map overrides in the block below
                If Not oFormChoice.oExplicitModelRenameMap.ContainsKey(kvpA.Key) Then
                    oFormChoice.oExplicitModelRenameMap(kvpA.Key) = kvpA.Value
                End If
            Next
        End If
    End If

    ' ── Pre-load preset map into form before it opens ──────────────────────
    If oPresetModelRenameMap IsNot Nothing AndAlso oPresetModelRenameMap.Count > 0 Then
        For Each kvp As System.Collections.Generic.KeyValuePair(Of String, String) In oPresetModelRenameMap
            oFormChoice.oExplicitModelRenameMap(kvp.Key) = kvp.Value
        Next
        Try : System.IO.File.AppendAllText(sLogFilePath, "PRESET-MAP: " & oPresetModelRenameMap.Count & " model renames pre-loaded into DrawingCopyMode form" & vbCrLf) : Catch : End Try
    End If

    If Not ShowDrawingModelRenameForm(oFormChoice, oPhase0Data) Then
        MessageBox.Show("Cancelled — no changes made.", "Drawing Copy Mode")
        Try : ThisApplication.iLogicVb.EventRuleManager.DisableEventRules = bOrigEventRules : Catch : End Try
        ThisApplication.SilentOperation = bOrigSilent
        Return
    End If

    ' ── 3c. Build rename map from user's edits: old full path → new full path ──
    Dim oRenameMap As New System.Collections.Generic.Dictionary(Of String, String)(StringComparer.OrdinalIgnoreCase)
    For Each kvp As System.Collections.Generic.KeyValuePair(Of String, String) In oFormChoice.oExplicitModelRenameMap
        Dim sOldBase As String = kvp.Key        ' no extension
        ' Defensively strip extension — user may have typed ".iam" in the form field.
        ' Extension is always taken from the original file so it is never doubled.
        Dim sNewBase As String = System.IO.Path.GetFileNameWithoutExtension(kvp.Value)
        If sNewBase = "" Then sNewBase = System.IO.Path.GetFileNameWithoutExtension(kvp.Key)
        If Not oBasenameToFullPath.ContainsKey(sOldBase) Then Continue For
        Dim sOldFull As String = oBasenameToFullPath(sOldBase)
        Dim sExt2 As String = System.IO.Path.GetExtension(sOldFull)   ' always from original
        Dim sNewFull As String = System.IO.Path.Combine(sTargetFolder, sNewBase & sExt2)
        oRenameMap(sOldFull) = sNewFull
        Try : System.IO.File.AppendAllText(sLogFilePath, "MAP: " & sOldBase & sExt2 & " -> " & sNewBase & sExt2 & vbCrLf) : Catch : End Try
    Next

    ' ── CATCH-ALL: drawing refs not covered by preset/form map ────────────────
    ' The preset map and Phase-A auto-detect cover the main GA tree.  But drawings
    ' commonly reference ancillary files that are NOT in the GA:
    '   • Transport / shipping assembly variants
    '   • Parts borrowed from other projects (PJ00141, PJ00165, …)
    '   • Mirror parts, detail parts placed only on a drawing sheet
    ' Without this sweep, those drawing refs are SILENTLY left pointing at the
    ' old file location — the copied drawing breaks when opened.
    '
    ' Logic: for every file in oAllModelPaths (all drawing refs across all drawings)
    ' that is NOT already covered by oRenameMap:
    '   1. Confirm the source file exists on disk (can't copy what isn't there).
    '   2. Derive a target name: apply prefix swap if the file starts with the
    '      detected old prefix; otherwise keep the original filename.
    '   3. Add old-full-path → new-full-path to oRenameMap so the normal copy
    '      phase and Phase 3 drawing FD rewrite handle it automatically.
    ' ────────────────────────────────────────────────────────────────────────────
    Dim iAncillaryAdded As Integer = 0
    Dim iAncillaryMissing As Integer = 0
    For Each sAncPath As String In oAllModelPaths
        ' Already handled by preset / form map?
        If oRenameMap.ContainsKey(sAncPath) Then Continue For
        ' Source must exist on disk — DART SHUT refs may point at checked-in files
        If Not System.IO.File.Exists(sAncPath) Then
            iAncillaryMissing += 1
            Try : System.IO.File.AppendAllText(sLogFilePath, "ANCILLARY-MISSING: " & System.IO.Path.GetFileName(sAncPath) & " — not on disk, skipped" & vbCrLf) : Catch : End Try
            Continue For
        End If
        ' Derive target filename: apply prefix swap when possible, else keep name
        Dim sAncBase As String = System.IO.Path.GetFileNameWithoutExtension(sAncPath)
        Dim sAncExt As String = System.IO.Path.GetExtension(sAncPath)
        Dim sAncNewBase As String = sAncBase
        If oOldPrefix <> "" AndAlso sNewPrefix <> "" Then
            If sAncNewBase.StartsWith(oOldPrefix & "-", StringComparison.OrdinalIgnoreCase) Then
                sAncNewBase = sNewPrefix & sAncNewBase.Substring(oOldPrefix.Length)
            ElseIf sAncNewBase.StartsWith(oOldPrefix & "_", StringComparison.OrdinalIgnoreCase) Then
                sAncNewBase = sNewPrefix & "-" & sAncNewBase.Substring(oOldPrefix.Length + 1)
            End If
        End If
        Dim sAncTarget As String = System.IO.Path.Combine(sTargetFolder, sAncNewBase & sAncExt)
        ' Don't add a no-op (file is already in target folder with same name)
        If String.Compare(sAncPath, sAncTarget, True) = 0 Then Continue For
        oRenameMap(sAncPath) = sAncTarget
        iAncillaryAdded += 1
        Try : System.IO.File.AppendAllText(sLogFilePath, "ANCILLARY-ADD: " & System.IO.Path.GetFileName(sAncPath) & " → " & System.IO.Path.GetFileName(sAncTarget) & vbCrLf) : Catch : End Try
    Next
    If iAncillaryAdded > 0 Then
        Try : System.IO.File.AppendAllText(sLogFilePath, "ANCILLARY-SWEEP: " & iAncillaryAdded & " file(s) added to copy map (not in preset/form; drawing ref will be updated), " & iAncillaryMissing & " not on disk." & vbCrLf) : Catch : End Try
    End If

    If oRenameMap.Count = 0 Then
        MessageBox.Show("No rename entries — nothing to do.", "Drawing Copy Mode")
        Try : ThisApplication.iLogicVb.EventRuleManager.DisableEventRules = bOrigEventRules : Catch : End Try
        ThisApplication.SilentOperation = bOrigSilent
        Return
    End If

    ' ── Write [RENAME_MAP] block to RunLog ─────────────────────────────
    Try
        Dim sbRenameMap As New System.Text.StringBuilder()
        sbRenameMap.AppendLine("[RENAME_MAP]")
        For Each kvpRm As System.Collections.Generic.KeyValuePair(Of String, String) In oRenameMap
            sbRenameMap.AppendLine(System.IO.Path.GetFileName(kvpRm.Key) & " = " & System.IO.Path.GetFileName(kvpRm.Value))
        Next
        sbRenameMap.AppendLine()
        System.IO.File.AppendAllText(sRunLogPath, sbRenameMap.ToString())
    Catch : End Try

    ' ══════════════════════════════════════════════════════════════════════
    ' GA VALIDATION — Open GA physically; walk its full tree; cross-check
    ' every drawing-mapped model against actual GA members.  Any file the
    ' drawings reference that does NOT appear anywhere in the GA tree is an
    ' "orphan" — copying it would create a file the GA never loads, so the
    ' user is warned before a single byte is copied.
    '
    ' Runs before the copy phase so it is cheap to cancel.  The GA is left
    ' open so the user can inspect it.  SilentOperation stays OFF during
    ' the validation so the Inventor window is visible.
    ' ══════════════════════════════════════════════════════════════════════
    Dim oGaValidDoc As AssemblyDocument = Nothing
    Dim bGaValidWasOpen As Boolean = False
    Dim oGaAllBasenames As New System.Collections.Generic.HashSet(Of String)(StringComparer.OrdinalIgnoreCase)
    ' Full-path lookup by basename — used by auto-resolve to reroute orphan copy sources to GA WIP equivalents
    Dim oGaFullPathsByBase As New System.Collections.Generic.Dictionary(Of String, String)(StringComparer.OrdinalIgnoreCase)

    If System.IO.File.Exists(sSelectedGaPath) Then
        Try
            ' Check if already open
            For Each oOpenChk As Document In ThisApplication.Documents
                If String.Compare(oOpenChk.FullFileName, sSelectedGaPath, True) = 0 Then
                    oGaValidDoc = TryCast(oOpenChk, AssemblyDocument)
                    bGaValidWasOpen = True
                    Exit For
                End If
            Next
            If oGaValidDoc Is Nothing Then
                ' Open GA visibly so user can see it
                ThisApplication.SilentOperation = False
                oGaValidDoc = TryCast(ThisApplication.Documents.Open(sSelectedGaPath, True), AssemblyDocument)
            End If
            Try : System.IO.File.AppendAllText(sLogFilePath, "GA-VALIDATE: opened " & System.IO.Path.GetFileName(sSelectedGaPath) & vbCrLf) : Catch : End Try

            ' Walk AllReferencedDocuments (every level) — collect basenames
            If oGaValidDoc IsNot Nothing Then
                Dim oGaRefDoc As Document
                For Each oGaRefDoc In oGaValidDoc.AllReferencedDocuments
                    Try
                        Dim sGaMem As String = System.IO.Path.GetFileNameWithoutExtension(oGaRefDoc.FullFileName)
                        If sGaMem <> "" Then
                            oGaAllBasenames.Add(sGaMem)
                            If Not oGaFullPathsByBase.ContainsKey(sGaMem) Then oGaFullPathsByBase.Add(sGaMem, oGaRefDoc.FullFileName)
                        End If
                    Catch : End Try
                Next
                ' Also add GA itself
                oGaAllBasenames.Add(System.IO.Path.GetFileNameWithoutExtension(sSelectedGaPath))
            End If
            Try : System.IO.File.AppendAllText(sLogFilePath, "GA-VALIDATE: " & oGaAllBasenames.Count & " unique members in GA tree" & vbCrLf) : Catch : End Try
        Catch exGaVal As Exception
            Try : System.IO.File.AppendAllText(sLogFilePath, "GA-VALIDATE-WARN: could not open GA for validation — " & exGaVal.Message & vbCrLf) : Catch : End Try
        End Try
    Else
        Try : System.IO.File.AppendAllText(sLogFilePath, "GA-VALIDATE-SKIP: GA path not found on disk — " & sSelectedGaPath & vbCrLf) : Catch : End Try
    End If

    ' Cross-check rename map against GA tree
    Dim oOrphans As New System.Collections.Generic.List(Of String)
    Dim oGaFound As New System.Collections.Generic.List(Of String)
    If oGaAllBasenames.Count > 0 Then
        For Each kvpChk As System.Collections.Generic.KeyValuePair(Of String, String) In oRenameMap
            Dim sChkBase As String = System.IO.Path.GetFileNameWithoutExtension(kvpChk.Key)
            If oGaAllBasenames.Contains(sChkBase) Then
                oGaFound.Add(sChkBase)
                Try : System.IO.File.AppendAllText(sLogFilePath, "GA-VALIDATE-OK: " & sChkBase & " found in GA tree" & vbCrLf) : Catch : End Try
            Else
                oOrphans.Add(sChkBase)
                Try : System.IO.File.AppendAllText(sLogFilePath, "GA-VALIDATE-ORPHAN: " & sChkBase & " NOT found in GA tree — drawing references file not in GA!" & vbCrLf) : Catch : End Try
            End If
        Next
    End If

    ' ── AUTO-RESOLVE ORPHANS — stem-match drawing-ref against GA WIP equivalents ──
    ' When a drawing references a PJ00161 original that is NOT in the GA (because
    ' the GA already has a WIP-renamed version), strip the project-number prefix
    ' (^[^-]+-[^-]+-) from the orphan basename to get a stem, then search GA basenames
    ' for any member whose name CONTAINS that stem.  If found, reroute the rename-map
    ' entry so the copy SOURCE is the GA WIP file, not the stale original.
    Dim oAutoResolved As New System.Collections.Generic.List(Of String)
    Dim oStillOrphans As New System.Collections.Generic.List(Of String)
    Dim oRxStrip As New System.Text.RegularExpressions.Regex("^[^-]+-[^-]+-", _
        System.Text.RegularExpressions.RegexOptions.None)

    If oGaFullPathsByBase.Count > 0 AndAlso oOrphans.Count > 0 Then
        For Each sOrphanBase As String In oOrphans
            Dim sStem As String = oRxStrip.Replace(sOrphanBase, "").Trim()
            If sStem = "" Then oStillOrphans.Add(sOrphanBase) : Continue For

            ' Search GA basenames for a member containing the stem
            Dim sGaMatchBase As String = ""
            For Each sGaCand As String In oGaAllBasenames
                If sGaCand.IndexOf(sStem, StringComparison.OrdinalIgnoreCase) >= 0 Then
                    sGaMatchBase = sGaCand
                    Exit For
                End If
            Next

            If sGaMatchBase <> "" AndAlso oGaFullPathsByBase.ContainsKey(sGaMatchBase) Then
                ' Find the rename-map entry for this orphan (match by key basename)
                Dim sOldKey As String = ""
                Dim sOldValue As String = ""
                For Each kvpScan As System.Collections.Generic.KeyValuePair(Of String, String) In oRenameMap
                    If System.IO.Path.GetFileNameWithoutExtension(kvpScan.Key).Equals(sOrphanBase, StringComparison.OrdinalIgnoreCase) Then
                        sOldKey = kvpScan.Key : sOldValue = kvpScan.Value : Exit For
                    End If
                Next
                If sOldKey <> "" Then
                    Dim sGaMatchFull As String = oGaFullPathsByBase(sGaMatchBase)
                    oRenameMap.Remove(sOldKey)
                    If Not oRenameMap.ContainsKey(sGaMatchFull) Then
                        oRenameMap.Add(sGaMatchFull, sOldValue)
                    End If
                    Try : System.IO.File.AppendAllText(sLogFilePath, "GA-RESOLVE: " & sOrphanBase & " → GA:" & sGaMatchBase & " → target:" & System.IO.Path.GetFileNameWithoutExtension(sOldValue) & vbCrLf) : Catch : End Try
                    oAutoResolved.Add("   " & sOrphanBase & vbCrLf & _
                                      "     → GA file:  " & sGaMatchBase & vbCrLf & _
                                      "     → target:   " & System.IO.Path.GetFileNameWithoutExtension(sOldValue))
                Else
                    oStillOrphans.Add(sOrphanBase)
                    Try : System.IO.File.AppendAllText(sLogFilePath, "GA-ORPHAN-UNRESOLVED: " & sOrphanBase & " (stem '" & sStem & "' matched GA member " & sGaMatchBase & " but no rename-map key found)" & vbCrLf) : Catch : End Try
                End If
            Else
                oStillOrphans.Add(sOrphanBase)
                Try : System.IO.File.AppendAllText(sLogFilePath, "GA-ORPHAN-UNRESOLVED: " & sOrphanBase & " (stem '" & sStem & "' not found in GA tree)" & vbCrLf) : Catch : End Try
            End If
        Next
    Else
        oStillOrphans.AddRange(oOrphans)
    End If

    ' Build and show validation summary popup (always — gives user confidence)
    Dim sbValMsg As New System.Text.StringBuilder()
    sbValMsg.AppendLine("═══ DRAWING COPY MODE — GA VALIDATION ═══")
    sbValMsg.AppendLine("GA:  " & System.IO.Path.GetFileName(sSelectedGaPath))
    sbValMsg.AppendLine("GA tree members: " & oGaAllBasenames.Count)
    sbValMsg.AppendLine()
    If oGaFound.Count > 0 Then
        sbValMsg.AppendLine("✔ CONFIRMED in GA tree (" & oGaFound.Count & "):")
        For Each sOk As String In oGaFound
            sbValMsg.AppendLine("   " & sOk)
        Next
    End If
    If oAutoResolved.Count > 0 Then
        sbValMsg.AppendLine()
        sbValMsg.AppendLine("✔ AUTO-RESOLVED (" & oAutoResolved.Count & ") — drawing ref was orphan but GA WIP equivalent found:")
        sbValMsg.AppendLine("  Copy SOURCE has been rerouted from the stale PJ##### original")
        sbValMsg.AppendLine("  to the GA's current WIP file so design changes are preserved.")
        sbValMsg.AppendLine()
        For Each sRes As String In oAutoResolved
            sbValMsg.AppendLine(sRes)
        Next
    End If
    ' Declare outside the If so the later Cancel check can see them
    Dim oAncillaryOk As New System.Collections.Generic.List(Of String)
    Dim oTrueOrphans As New System.Collections.Generic.List(Of String)
    If oStillOrphans.Count > 0 Then
        ' Partition: orphans that ARE in the catch-all sweep (will be copied ok) vs
        ' those NOT on disk at all (genuine problem).
        For Each sOrph As String In oStillOrphans
            ' Find the full path for this orphan basename
            Dim sOrphFull As String = ""
            For Each sAncCand As String In oAllModelPaths
                If System.IO.Path.GetFileNameWithoutExtension(sAncCand).Equals(sOrph, StringComparison.OrdinalIgnoreCase) Then
                    sOrphFull = sAncCand : Exit For
                End If
            Next
            Dim bInRenameMap As Boolean = sOrphFull <> "" AndAlso oRenameMap.ContainsKey(sOrphFull)
            If bInRenameMap Then
                oAncillaryOk.Add(sOrph)
            Else
                oTrueOrphans.Add(sOrph)
            End If
        Next

        If oAncillaryOk.Count > 0 Then
            sbValMsg.AppendLine()
            sbValMsg.AppendLine("ℹ ANCILLARY — not in GA, copied independently (" & oAncillaryOk.Count & "):")
            sbValMsg.AppendLine("  These files are referenced by drawings but are NOT in the GA tree.")
            sbValMsg.AppendLine("  This is normal for transport variants, borrowed parts from other")
            sbValMsg.AppendLine("  projects, mirror parts, etc.  They will be copied to the target")
            sbValMsg.AppendLine("  folder and all drawing refs will be updated automatically.")
            sbValMsg.AppendLine()
            For Each sAnc As String In oAncillaryOk
                sbValMsg.AppendLine("   ℹ " & sAnc)
            Next
        End If

        If oTrueOrphans.Count > 0 Then
            sbValMsg.AppendLine()
            sbValMsg.AppendLine("⚠ WARNING — NOT ON DISK (" & oTrueOrphans.Count & "):")
            sbValMsg.AppendLine("  These files are referenced by drawings but cannot be found on")
            sbValMsg.AppendLine("  disk.  They cannot be copied — drawing refs to them will remain")
            sbValMsg.AppendLine("  pointing at the original (possibly Vault checked-in) location.")
            sbValMsg.AppendLine()
            For Each sTrueOrph As String In oTrueOrphans
                sbValMsg.AppendLine("   ⚠ " & sTrueOrph)
            Next
            sbValMsg.AppendLine()
            sbValMsg.AppendLine("Continue anyway, or Cancel to investigate?")
        End If
    Else
        If oGaAllBasenames.Count > 0 Then
            Dim sResolvedNote As String = If(oAutoResolved.Count > 0, " (" & oAutoResolved.Count & " auto-resolved from WIP)", "")
            sbValMsg.AppendLine("All drawing-mapped models confirmed or auto-resolved in GA tree" & sResolvedNote & ".  Safe to proceed.")
        Else
            sbValMsg.AppendLine("(GA validation skipped — GA could not be read)")
        End If
    End If

    Dim oValResult As System.Windows.Forms.DialogResult
    ' Only block with Cancel when files are genuinely NOT on disk — those can't be copied.
    ' Ancillary files (covered by the catch-all sweep) are fine to proceed without Cancel.
    Dim bHasTrueOrphans As Boolean = False
    bHasTrueOrphans = (oTrueOrphans.Count > 0)
    If bHasTrueOrphans Then
        oValResult = MessageBox.Show(sbValMsg.ToString(), "GA Validation — Files Not On Disk", _
            System.Windows.Forms.MessageBoxButtons.OKCancel, System.Windows.Forms.MessageBoxIcon.Warning)
        If oValResult = System.Windows.Forms.DialogResult.Cancel Then
            MessageBox.Show("Cancelled — no files copied.", "Drawing Copy Mode")
            If Not bGaValidWasOpen AndAlso oGaValidDoc IsNot Nothing Then
                Try : oGaValidDoc.Close(False) : Catch : End Try
            End If
            Try : ThisApplication.iLogicVb.EventRuleManager.DisableEventRules = bOrigEventRules : Catch : End Try
            ThisApplication.SilentOperation = bOrigSilent
            Return
        End If
    ElseIf oStillOrphans.Count > 0 Then
        ' Ancillary files only — info popup, no Cancel needed
        MessageBox.Show(sbValMsg.ToString(), "GA Validation — Ancillary Files (Safe to Proceed)", _
            System.Windows.Forms.MessageBoxButtons.OK, System.Windows.Forms.MessageBoxIcon.Information)
    Else
        MessageBox.Show(sbValMsg.ToString(), "GA Validation — OK to Proceed", _
            System.Windows.Forms.MessageBoxButtons.OK, System.Windows.Forms.MessageBoxIcon.Information)
    End If

    ' ── 4. File.Copy each model; open copy in session ───────────────────
    ThisApplication.SilentOperation = True
    Dim oCopiedPairs As New System.Collections.Generic.List(Of Object())  ' {oldPath, newPath}
    Dim iCopyOk As Integer = 0
    Dim iCopySkip As Integer = 0
    Dim iCopyFail As Integer = 0

    For Each kvp As System.Collections.Generic.KeyValuePair(Of String, String) In oRenameMap
        Dim sOldFull As String = kvp.Key
        Dim sNewFull As String = kvp.Value
        Dim sNewBaseFn As String = System.IO.Path.GetFileName(sNewFull)

        ' Skip copy if already present (re-run)
        If System.IO.File.Exists(sNewFull) Then
            Try : System.IO.File.AppendAllText(sLogFilePath, "COPY-SKIP (exists): " & sNewBaseFn & vbCrLf) : Catch : End Try
            iCopySkip = iCopySkip + 1
        Else
            Try
                System.IO.File.Copy(sOldFull, sNewFull, False)
                iCopyOk = iCopyOk + 1
                Try : System.IO.File.AppendAllText(sLogFilePath, "COPY-OK: " & sNewBaseFn & vbCrLf) : Catch : End Try
            Catch exCopy As Exception
                iCopyFail = iCopyFail + 1
                Try : System.IO.File.AppendAllText(sLogFilePath, "COPY-FAIL: " & sNewBaseFn & " : " & exCopy.Message & vbCrLf) : Catch : End Try
                Continue For
            End Try
        End If

        ' Track rename pairs for the replace pass (no need to open in session)
        oCopiedPairs.Add(New Object() {sOldFull, sNewFull})
    Next

    Try : System.IO.File.AppendAllText(sLogFilePath, "Copy phase: " & iCopyOk & " new, " & iCopySkip & " skipped, " & iCopyFail & " failed." & vbCrLf) : Catch : End Try

    If oCopiedPairs.Count = 0 Then
        MessageBox.Show("No model copies were made or found — nothing to replace." & vbCrLf & "Check log: " & sLogFilePath, "Drawing Copy Mode")
        Try : ThisApplication.iLogicVb.EventRuleManager.DisableEventRules = bOrigEventRules : Catch : End Try
        ThisApplication.SilentOperation = bOrigSilent
        Return
    End If

    ' ── 4b. Abort if any copy failed — atomicity contract ───────────────
    ' Per RMAD SSA verdict (runs/clean-sweeper-execution-order/SSA-output.md):
    ' ALL copies must succeed before any relinking begins. A partial copy tree
    ' produces an un-revertable mixed state. Originals are untouched — rollback
    ' is simply "delete the target folder".
    If iCopyFail > 0 Then
        Try : System.IO.File.AppendAllText(sLogFilePath, "ABORT: " & iCopyFail & " copy failure(s) — assembly relink and drawing update skipped." & vbCrLf) : Catch : End Try
        Try : ThisApplication.iLogicVb.EventRuleManager.DisableEventRules = bOrigEventRules : Catch : End Try
        ThisApplication.SilentOperation = bOrigSilent
        MessageBox.Show("COPY FAILED: " & iCopyFail & " file(s) could not be copied." & vbCrLf & vbCrLf & _
            "Assembly relink and drawing update ABORTED — no originals were modified." & vbCrLf & _
            "Fix the copy failures and re-run." & vbCrLf & vbCrLf & "Log: " & sLogFilePath, _
            "Drawing Copy Mode — Aborted")
        Return
    End If

    ' ── 4c. Phase 3 — Relink assembly tree (before touching any drawings) ──
    ' Per RMAD SSA verdict: ALL .iam/.ipt files in the rename map must have
    ' their internal FileDescriptors updated to new paths BEFORE drawing pass.
    ' The GA rename map is the single source of truth. Order: deepest first
    ' (longest path), GA last.
    Dim iAsmRelinkOk As Integer = 0
    Dim iAsmRelinkFail As Integer = 0
    Dim iAsmRelinkSkip As Integer = 0
    Try : System.IO.File.AppendAllText(sLogFilePath, vbCrLf & "PHASE-3: Assembly relink starting..." & vbCrLf) : Catch : End Try
    RunAssemblyRelinkPass(oRenameMap, sLogFilePath, iAsmRelinkOk, iAsmRelinkFail, iAsmRelinkSkip)
    Try : System.IO.File.AppendAllText(sLogFilePath, "PHASE-3: done — " & iAsmRelinkOk & " saved, " & iAsmRelinkSkip & " no-change, " & iAsmRelinkFail & " failed." & vbCrLf & vbCrLf) : Catch : End Try

    ' ── 5. Replace references in ALL drawings via FileDescriptor API ────
    ' For each drawing that has refs in the rename map:
    '   - Active drawing: use ThisDoc.Document directly (already open, no close)
    '   - Sibling: check if open; if not open silently, replace, save, close
    ' FileDescriptor.ReplaceReference(newPath) works by path — no model doc needed.
    '
    ' Event-driven rules already disabled at function entry (before Phase 1 scan).
    ' Re-enable SilentOperation for the drawing replace phase to suppress unneeded prompts.
    ThisApplication.SilentOperation = True
    Dim iDwgOkCM As Integer = 0
    Dim iDwgFailCM As Integer = 0
    Dim iTotalRepOk As Integer = 0
    Dim iRepDwgIdx As Integer
    For iRepDwgIdx = 0 To oAllDwgPaths.Count - 1
        Dim sRepDwgPath As String = oAllDwgPaths(iRepDwgIdx)
        ' Respect the include/exclude tick from the form
        Dim sRepDwgBase As String = System.IO.Path.GetFileName(sRepDwgPath)
        Dim bIncluded As Boolean = True
        oFormChoice.oDrawingStateMatch.TryGetValue(sRepDwgBase, bIncluded)
        If Not bIncluded Then
            Try : System.IO.File.AppendAllText(sLogFilePath, "DRAW-SKIP (excluded by user): " & sRepDwgBase & vbCrLf) : Catch : End Try
            Continue For
        End If
        If Not oAllDwgRefs.ContainsKey(sRepDwgPath) Then Continue For
        Dim oRepRefs As System.Collections.Generic.List(Of String) = oAllDwgRefs(sRepDwgPath)
        ' Quick check: does this drawing have any ref in the rename map?
        Dim bHasMatch As Boolean = False
        Dim iMatchChk As Integer
        For iMatchChk = 0 To oRepRefs.Count - 1
            If oRenameMap.ContainsKey(oRepRefs(iMatchChk)) Then bHasMatch = True : Exit For
        Next
        If Not bHasMatch Then
            Try : System.IO.File.AppendAllText(sLogFilePath, "DRAW-SKIP (no matching refs): " & System.IO.Path.GetFileName(sRepDwgPath) & vbCrLf) : Catch : End Try
            Continue For
        End If

        ' Get document object
        Dim oRepDoc As Object = Nothing
        Dim bOpenedRepDoc As Boolean = False
        If String.Compare(sRepDwgPath, sActiveDwgPath, True) = 0 Then
            oRepDoc = ThisDoc.Document
        Else
            Try : oRepDoc = ThisApplication.Documents.ItemByName(sRepDwgPath) : Catch : End Try
            If oRepDoc Is Nothing Then
                Try
                    oRepDoc = ThisApplication.Documents.Open(sRepDwgPath, False)
                    bOpenedRepDoc = True
                Catch exRepOpen As Exception
                    Try : System.IO.File.AppendAllText(sLogFilePath, "DRAW-OPEN-FAIL: " & System.IO.Path.GetFileName(sRepDwgPath) & " : " & exRepOpen.Message & vbCrLf) : Catch : End Try
                    iDwgFailCM = iDwgFailCM + 1
                    Continue For
                End Try
            End If
        End If

        ' FileDescriptor replace loop
        Dim iRepOkDwg As Integer = 0
        Dim iRepFailDwg As Integer = 0
        Try
            Dim oRepDocFile As Object = oRepDoc.File
            For Each oRepRefFile As Object In oRepDocFile.ReferencedFileDescriptors
                Dim sRepRefFull As String = ""
                Try : sRepRefFull = oRepRefFile.FullFileName : Catch : Continue For : End Try
                If oRenameMap.ContainsKey(sRepRefFull) Then
                    Dim sRepNewFull As String = oRenameMap(sRepRefFull)
                    ' Skip if old and new path are identical — nothing to do
                    If String.Compare(sRepRefFull, sRepNewFull, True) = 0 Then Continue For
                    Try
                        oRepRefFile.ReplaceReference(sRepNewFull)
                        iRepOkDwg = iRepOkDwg + 1
                        iTotalRepOk = iTotalRepOk + 1
                        Try : System.IO.File.AppendAllText(sLogFilePath, "REPLACE-OK [" & System.IO.Path.GetFileName(sRepDwgPath) & "]: " & System.IO.Path.GetFileName(sRepRefFull) & " -> " & System.IO.Path.GetFileName(sRepNewFull) & vbCrLf) : Catch : End Try
                    Catch exRepFD As Exception
                        iRepFailDwg = iRepFailDwg + 1
                        Try : System.IO.File.AppendAllText(sLogFilePath, "REPLACE-FAIL [" & System.IO.Path.GetFileName(sRepDwgPath) & "]: " & System.IO.Path.GetFileName(sRepRefFull) & " : " & exRepFD.Message & vbCrLf) : Catch : End Try
                    End Try
                ElseIf Not System.IO.File.Exists(sRepRefFull) Then
                    ' Ref not in rename map AND file no longer exists on disk → orphan
                    ' (A ref not in map but on disk is a live cross-project ref — not an error)
                    Try : System.IO.File.AppendAllText(sLogFilePath, "DRAW-ORPHAN-WARN [" & System.IO.Path.GetFileName(sRepDwgPath) & "]: ref not in map and file missing — " & sRepRefFull & vbCrLf) : Catch : End Try
                End If
            Next
        Catch exRepFdOuter As Exception
            iRepFailDwg = iRepFailDwg + 1
            Try : System.IO.File.AppendAllText(sLogFilePath, "FILEDESC-FAIL [" & System.IO.Path.GetFileName(sRepDwgPath) & "]: " & exRepFdOuter.Message & vbCrLf) : Catch : End Try
        End Try

        ' Update + save if any refs changed
        If iRepOkDwg > 0 AndAlso iRepFailDwg = 0 Then
            If String.Compare(sRepDwgPath, sActiveDwgPath, True) = 0 Then
                Try : InventorVb.DocumentUpdate() : Catch : End Try
            Else
                Try : oRepDoc.Update() : Catch : End Try
            End If
            Try
                Dim sRepDwgPathFull As String = CStr(oRepDoc.FullDocumentName)
                Try
                    Dim oRepAttrs As System.IO.FileAttributes = System.IO.File.GetAttributes(sRepDwgPathFull)
                    If (oRepAttrs And System.IO.FileAttributes.ReadOnly) = System.IO.FileAttributes.ReadOnly Then
                        System.IO.File.SetAttributes(sRepDwgPathFull, oRepAttrs And Not System.IO.FileAttributes.ReadOnly)
                    End If
                Catch
                End Try
                oRepDoc.Save()
                iDwgOkCM = iDwgOkCM + 1
                Try : System.IO.File.AppendAllText(sLogFilePath, "DRAW-SAVED-OK: " & System.IO.Path.GetFileName(sRepDwgPath) & vbCrLf) : Catch : End Try
            Catch exRepSave As Exception
                iDwgFailCM = iDwgFailCM + 1
                Try : System.IO.File.AppendAllText(sLogFilePath, "DRAW-SAVE-FAIL: " & System.IO.Path.GetFileName(sRepDwgPath) & " : " & exRepSave.Message & vbCrLf) : Catch : End Try
            End Try
        ElseIf iRepFailDwg > 0 Then
            iDwgFailCM = iDwgFailCM + 1
            Try : System.IO.File.AppendAllText(sLogFilePath, "DRAW-NOT-SAVED (replace errors): " & System.IO.Path.GetFileName(sRepDwgPath) & vbCrLf) : Catch : End Try
        End If

        If bOpenedRepDoc Then
            Try : oRepDoc.Close(True) : Catch : End Try
        End If
    Next
    Try : ThisApplication.iLogicVb.EventRuleManager.DisableEventRules = bOrigEventRules : Catch : End Try
    ThisApplication.SilentOperation = bOrigSilent

    ' ── 5b. Internal reference rewrite (Phase 3-style, after drawing pass) ──
    ' The copied GA / sub-assemblies can still point at the OLD children.
    ' Open each NEW .iam in oRenameMap, walk File.ReferencedFileDescriptors and
    ' ReplaceReference any old path found in oRenameMap with its new path.
    ' Save the assembly only if something changed. Puts the Drawing-referenced
    ' models into the new GA tree before the Full Clean Sweep prompt.
    Dim iIntAsmSaved As Integer = 0
    Dim iIntAsmFail As Integer = 0
    Dim kvpInt As System.Collections.Generic.KeyValuePair(Of String, String)
    Dim sIntAsmPath As String
    Dim sIntAsmName As String
    Dim oIntDoc As Object
    Dim bIntOpened As Boolean
    Dim iIntChanged As Integer
    Dim oIntFD As Object
    Dim sIntRefFull As String
    Dim sIntTarget As String
    Dim oIntAttrs As System.IO.FileAttributes
    ThisApplication.SilentOperation = True
    Try
        ThisApplication.iLogicVb.EventRuleManager.DisableEventRules = True
    Catch
    End Try
    Try
        System.IO.File.AppendAllText(sLogFilePath, vbCrLf & "INTERNAL-REWRITE: starting (new .iam files in rename map)..." & vbCrLf)
    Catch
    End Try
    For Each kvpInt In oRenameMap
        sIntAsmPath = kvpInt.Value
        If Not sIntAsmPath.EndsWith(".iam", StringComparison.OrdinalIgnoreCase) Then Continue For
        sIntAsmName = System.IO.Path.GetFileName(sIntAsmPath)
        If Not System.IO.File.Exists(sIntAsmPath) Then
            iIntAsmFail = iIntAsmFail + 1
            Try
                System.IO.File.AppendAllText(sLogFilePath, "INTERNAL-FAIL: " & sIntAsmName & " : new file not found on disk" & vbCrLf)
            Catch
            End Try
            Continue For
        End If
        oIntDoc = Nothing
        bIntOpened = False
        iIntChanged = 0
        Try
            oIntDoc = ThisApplication.Documents.ItemByName(sIntAsmPath)
        Catch
            oIntDoc = Nothing
        End Try
        Try
            If oIntDoc Is Nothing Then
                oIntDoc = ThisApplication.Documents.Open(sIntAsmPath, False)
                bIntOpened = True
            End If
            For Each oIntFD In oIntDoc.File.ReferencedFileDescriptors
                sIntRefFull = ""
                Try
                    sIntRefFull = CStr(oIntFD.FullFileName)
                Catch
                    sIntRefFull = ""
                End Try
                If sIntRefFull = "" Then Continue For
                If Not oRenameMap.ContainsKey(sIntRefFull) Then Continue For
                sIntTarget = oRenameMap(sIntRefFull)
                If String.Compare(sIntRefFull, sIntTarget, True) = 0 Then Continue For
                If Not System.IO.File.Exists(sIntTarget) Then
                    Try
                        System.IO.File.AppendAllText(sLogFilePath, "INTERNAL-FAIL: " & sIntAsmName & " : target missing " & System.IO.Path.GetFileName(sIntTarget) & vbCrLf)
                    Catch
                    End Try
                    Continue For
                End If
                Try
                    oIntFD.ReplaceReference(sIntTarget)
                    iIntChanged = iIntChanged + 1
                    Try
                        System.IO.File.AppendAllText(sLogFilePath, "INTERNAL FD: " & sIntAsmName & " : " & System.IO.Path.GetFileName(sIntRefFull) & " -> " & System.IO.Path.GetFileName(sIntTarget) & vbCrLf)
                    Catch
                    End Try
                Catch exIntFD As Exception
                    Try
                        System.IO.File.AppendAllText(sLogFilePath, "INTERNAL-FAIL: " & sIntAsmName & " : " & System.IO.Path.GetFileName(sIntRefFull) & " : " & exIntFD.Message & vbCrLf)
                    Catch
                    End Try
                End Try
            Next
            If iIntChanged > 0 Then
                Try
                    oIntAttrs = System.IO.File.GetAttributes(sIntAsmPath)
                    If (oIntAttrs And System.IO.FileAttributes.ReadOnly) = System.IO.FileAttributes.ReadOnly Then
                        System.IO.File.SetAttributes(sIntAsmPath, oIntAttrs And Not System.IO.FileAttributes.ReadOnly)
                    End If
                Catch
                End Try
                Try
                    oIntDoc.Update()
                Catch
                End Try
                oIntDoc.Save()
                iIntAsmSaved = iIntAsmSaved + 1
                Try
                    System.IO.File.AppendAllText(sLogFilePath, "INTERNAL-SAVED: " & sIntAsmName & " (" & iIntChanged & " ref(s) rewritten)" & vbCrLf)
                Catch
                End Try
            End If
        Catch exInt As Exception
            iIntAsmFail = iIntAsmFail + 1
            Try
                System.IO.File.AppendAllText(sLogFilePath, "INTERNAL-FAIL: " & sIntAsmName & " : " & exInt.Message & vbCrLf)
            Catch
            End Try
        End Try
        If bIntOpened AndAlso oIntDoc IsNot Nothing Then
            Try
                oIntDoc.Close(True)
            Catch
            End Try
        End If
    Next
    Try
        System.IO.File.AppendAllText(sLogFilePath, "INTERNAL-REWRITE: done - " & iIntAsmSaved & " assembly(ies) saved, " & iIntAsmFail & " failed." & vbCrLf)
    Catch
    End Try
    Try
        ThisApplication.iLogicVb.EventRuleManager.DisableEventRules = bOrigEventRules
    Catch
    End Try
    ThisApplication.SilentOperation = bOrigSilent

    ' ── 6. Summary ──────────────────────────────────────────────────────
    Dim sSummary As String = ""
    If iDwgOkCM > 0 AndAlso iDwgFailCM = 0 AndAlso iAsmRelinkFail = 0 Then
        sSummary = "Complete." & vbCrLf & _
            "Models copied: " & (iCopyOk + iCopySkip) & "  (" & iCopySkip & " already existed)" & vbCrLf & _
            "Assembly refs relinked: " & iAsmRelinkOk & " files  (" & iAsmRelinkSkip & " no-change)" & vbCrLf & _
            "Drawings updated & saved: " & iDwgOkCM & vbCrLf & _
            "Total ref swaps: " & iTotalRepOk
    ElseIf iAsmRelinkFail > 0 Then
        sSummary = "WARNING — " & iAsmRelinkFail & " assembly relink failure(s)." & vbCrLf & _
            "GA tree may not be fully rewired.  Check log for ASMRELINK-FAIL entries." & vbCrLf & _
            "Drawings updated & saved: " & iDwgOkCM
    ElseIf iDwgOkCM > 0 Then
        sSummary = "Partial — " & iDwgOkCM & " drawing(s) saved, " & iDwgFailCM & " failed." & vbCrLf & "Check log for details."
    Else
        sSummary = "No drawings were updated." & vbCrLf & "Models copied: " & (iCopyOk + iCopySkip) & vbCrLf & "Check log for details."
    End If

    Try : System.IO.File.AppendAllText(sLogFilePath, vbCrLf & "Done: " & DateTime.Now.ToString() & vbCrLf) : Catch : End Try

    ThisApplication.SilentOperation = bOrigSilent
    MessageBox.Show(sSummary & vbCrLf & vbCrLf & "Log: " & sLogFilePath, "Drawing Copy Mode — Complete")

    ' ── 7. Offer to continue with full GA Assembly Clean Sweep ──────────
    Dim bDoFullSweep As Boolean = False
    Try
        Dim oSweepForm As New System.Windows.Forms.Form()
        oSweepForm.Text = "Clean Sweeper — Drawing Copy Complete"
        oSweepForm.Width = 420
        oSweepForm.Height = 230
        oSweepForm.FormBorderStyle = System.Windows.Forms.FormBorderStyle.FixedDialog
        oSweepForm.StartPosition = System.Windows.Forms.FormStartPosition.CenterScreen
        oSweepForm.MaximizeBox = False
        oSweepForm.MinimizeBox = False

        ' ── Status banner (no System.Drawing refs — iLogic sandbox blocks Color/Font) ──
        Dim oBannerLbl As New System.Windows.Forms.Label()
        oBannerLbl.Text = "[ OK ]  Drawings updated successfully"
        oBannerLbl.Left = 16 : oBannerLbl.Top = 14 : oBannerLbl.Width = 380 : oBannerLbl.Height = 20
        oSweepForm.Controls.Add(oBannerLbl)

        ' ── Question label ──
        Dim oQlbl As New System.Windows.Forms.Label()
        oQlbl.Text = "What would you like to do next?"
        oQlbl.Left = 16 : oQlbl.Top = 42 : oQlbl.Width = 380 : oQlbl.Height = 20
        oSweepForm.Controls.Add(oQlbl)

        ' ── Option A — Full Sweep ──
        Dim oRbFull As New System.Windows.Forms.RadioButton()
        oRbFull.Text = "CONTINUE? — Run Full GA Assembly Clean Sweep"
        oRbFull.Left = 16 : oRbFull.Top = 68 : oRbFull.Width = 370 : oRbFull.Height = 22
        oRbFull.Checked = True
        oSweepForm.Controls.Add(oRbFull)

        ' ── Option B — Done ──
        Dim oRbDone As New System.Windows.Forms.RadioButton()
        oRbDone.Text = "FINISH HERE?  Drawings are Done.  No Sweep Required."
        oRbDone.Left = 16 : oRbDone.Top = 94 : oRbDone.Width = 370 : oRbDone.Height = 22
        oSweepForm.Controls.Add(oRbDone)

        ' ── Buttons ──
        Dim oBtnOk As New System.Windows.Forms.Button()
        oBtnOk.Text = "OK"
        oBtnOk.Width = 90 : oBtnOk.Height = 28
        oBtnOk.Left = 200 : oBtnOk.Top = 136
        oBtnOk.DialogResult = System.Windows.Forms.DialogResult.OK
        oSweepForm.Controls.Add(oBtnOk)

        Dim oBtnCancel As New System.Windows.Forms.Button()
        oBtnCancel.Text = "Cancel"
        oBtnCancel.Width = 90 : oBtnCancel.Height = 28
        oBtnCancel.Left = 300 : oBtnCancel.Top = 136
        oBtnCancel.DialogResult = System.Windows.Forms.DialogResult.Cancel
        oSweepForm.Controls.Add(oBtnCancel)

        oSweepForm.AcceptButton = oBtnOk
        oSweepForm.CancelButton = oBtnCancel

        Dim oSweepDlg As System.Windows.Forms.DialogResult = oSweepForm.ShowDialog()
        If oSweepDlg = System.Windows.Forms.DialogResult.OK AndAlso oRbFull.Checked Then
            bDoFullSweep = True
        End If
    Catch exDlg As Exception
        ' Fallback to simple messagebox if form fails to render
        Dim oFbResult As System.Windows.Forms.DialogResult = MessageBox.Show(
            "Drawings are updated." & vbCrLf & vbCrLf &
            "Continue with full Assembly Clean Sweep?",
            "Full Clean Sweep?",
            System.Windows.Forms.MessageBoxButtons.YesNo,
            System.Windows.Forms.MessageBoxIcon.Question)
        bDoFullSweep = (oFbResult = System.Windows.Forms.DialogResult.Yes)
    End Try

    If bDoFullSweep Then
        Dim sGaToOpen As String = ""
        For Each kvpGA As System.Collections.Generic.KeyValuePair(Of String, String) In oRenameMap
            If System.IO.Path.GetExtension(kvpGA.Value).ToUpper() = ".IAM" Then
                sGaToOpen = kvpGA.Value
                Exit For
            End If
        Next
        If sGaToOpen <> "" AndAlso System.IO.File.Exists(sGaToOpen) Then
            Try
                Dim oGaDoc As AssemblyDocument = CType(ThisApplication.Documents.Open(sGaToOpen, True), AssemblyDocument)

                ' Detect the real old prefix(es) by scanning the GA's referenced docs.
                ' Only accept PJ#####-format project numbers — ignore AS standards,
                ' content centre parts, and any other non-project prefixes.
                ' Collect ALL distinct old PJ prefixes (e.g. PJ00193, PJ00180, PJ00190)
                ' so every legacy sub is caught in one sweep.
                Dim oOldPrefixSet As New System.Collections.Generic.HashSet(Of String)(StringComparer.OrdinalIgnoreCase)
                Try
                    For Each oRefDoc As Document In oGaDoc.AllReferencedDocuments
                        Dim sRefBase As String = System.IO.Path.GetFileNameWithoutExtension(oRefDoc.FullFileName)
                        Dim iRefDash As Integer = sRefBase.IndexOf("-"c)
                        If iRefDash < 2 Then Continue For
                        Dim sRefPfx As String = sRefBase.Substring(0, iRefDash)
                        ' Must be a PJ-number: starts with "PJ" followed by digits only
                        If Not sRefPfx.ToUpper().StartsWith("PJ") Then Continue For
                        Dim sDigits As String = sRefPfx.Substring(2)
                        Dim bAllDigits As Boolean = sDigits.Length >= 3
                        For Each c As Char In sDigits
                            If Not Char.IsDigit(c) Then bAllDigits = False : Exit For
                        Next
                        If Not bAllDigits Then Continue For
                        ' Skip if it IS the new prefix
                        If String.Compare(sRefPfx, sNewPrefix, True) = 0 Then Continue For
                        oOldPrefixSet.Add(sRefPfx)
                    Next
                Catch
                    ' AllReferencedDocuments can throw E_FAIL on some trees
                End Try

                ' Use the first detected prefix as the primary (drives the batch form pre-fill).
                ' All detected prefixes are logged so the user can verify.
                Dim sOldPrefixForSweep As String = ""
                If oOldPrefixSet.Count > 0 Then
                    For Each s As String In oOldPrefixSet
                        sOldPrefixForSweep = s
                        Exit For
                    Next
                End If
                Dim sAllOldPfx As String = String.Join(", ", New System.Collections.Generic.List(Of String)(oOldPrefixSet).ToArray())
                Try : System.IO.File.AppendAllText(sLogFilePath, "FULL-SWEEP: old PJ-prefix(es) detected from GA refs = '" & sAllOldPfx & "'  (using '" & sOldPrefixForSweep & "' as primary)" & vbCrLf) : Catch : End Try
                RunAssemblyTraverseMode(oGaDoc, System.IO.Path.GetDirectoryName(sGaToOpen), sOldPrefixForSweep, oPresetModelRenameMap)
            Catch exGA As Exception
                MessageBox.Show("Could not open GA assembly: " & exGA.Message & vbCrLf & "Open it manually and re-run the rule.", "Full Sweep — Open Failed")
            End Try
        Else
            MessageBox.Show("Could not locate the GA assembly automatically." & vbCrLf & "Open it manually and re-run the rule.", "Full Sweep")
        End If
    End If

End Sub


Sub RunDrawingUpdatePass( _
    oIdwFileList As System.Collections.Generic.List(Of String), _
    oRenameMap As System.Collections.Generic.Dictionary(Of String, String), _
    oDrawingStateMatch As System.Collections.Generic.Dictionary(Of String, Boolean), _
    oLog As System.Text.StringBuilder, _
    ByRef iDwgOk As Integer, _
    ByRef iDwgPartial As Integer, _
    ByRef iDwgFail As Integer, _
    sLogFilePath As String)

    If oRenameMap Is Nothing OrElse oRenameMap.Count = 0 Then
        oLog.Append(vbCrLf & "DRAWING UPDATE: rename map is empty - nothing to do.")
        Return
    End If

    If oIdwFileList Is Nothing OrElse oIdwFileList.Count = 0 Then
        oLog.Append(vbCrLf & "DRAWING UPDATE: no drawings in selection - nothing to do.")
        Return
    End If

    Dim oIdwFiles() As String = oIdwFileList.ToArray()

    oLog.Append(vbCrLf & "DRAWING UPDATE: processing " & oIdwFiles.Length & " selected drawing(s).")
    Try : System.IO.File.AppendAllText(sLogFilePath, "Drawing update: " & oIdwFiles.Length & " drawing(s) selected." & vbCrLf) : Catch : End Try

    Dim bOrigSilent As Boolean = ThisApplication.SilentOperation
    ThisApplication.SilentOperation = True

    For Each sDrawPath As String In oIdwFiles
        Dim oDrawDoc As DrawingDocument = Nothing
        Try
            ' Open drawing without showing it in the UI
            oDrawDoc = TryCast(ThisApplication.Documents.Open(sDrawPath, False), DrawingDocument)
            If oDrawDoc Is Nothing Then
                oLog.Append(vbCrLf & "DRAW-SKIP (not a drawing): " & System.IO.Path.GetFileName(sDrawPath))
                iDwgFail = iDwgFail + 1
                Continue For
            End If

            ' Suppress event-driven rules (e.g. Working Drawing Stamp) for the
            ' duration of this pass — prevents missing-rule dialogs from blocking the run.
            Try : oDrawDoc.iLogicVb.EventRuleManager.DisableEventRules = True : Catch : End Try

            ' --- Phase A: collect which refs need updating ---
            ' Build a list of (oldDoc, newPath) pairs from oRenameMap
            Dim oSwaps As New System.Collections.Generic.List(Of Object())  ' {oldDoc, newFullPath}
            For Each oRef As Document In oDrawDoc.ReferencedDocuments
                Dim sRefPath As String = ""
                Try : sRefPath = oRef.FullDocumentName : Catch : Continue For : End Try
                Dim sNewPath As String = ""
                If oRenameMap.TryGetValue(sRefPath, sNewPath) Then
                    ' Verify new doc is open in session
                    Dim oNewDoc As Document = Nothing
                    Try
                        oNewDoc = ThisApplication.Documents.ItemByName(sNewPath)
                    Catch
                    End Try
                    If oNewDoc IsNot Nothing Then
                        oSwaps.Add(New Object() {oRef, oNewDoc, sRefPath, sNewPath})
                    Else
                        ' New doc not in session - log and skip this swap
                        oLog.Append(vbCrLf & "DRAW-REF-NOTSESSION: " & System.IO.Path.GetFileName(sDrawPath) & " -> " & System.IO.Path.GetFileName(sNewPath) & " (new doc not open in session)")
                        Try : System.IO.File.AppendAllText(sLogFilePath, "DRAW-REF-NOTSESSION: " & sDrawPath & " -> " & sNewPath & vbCrLf) : Catch : End Try
                    End If
                End If
            Next

            ' --- Phase B: apply ReplaceReference for each swap ---
            ' ReferencedDocuments is a DocumentsEnumerator and has no ReplaceReference.
            ' Use the drawing's File.ReferencedFileDescriptors instead.
            Dim iSwapOk As Integer = 0
            Dim iSwapFail As Integer = 0
            For Each oSwap As Object() In oSwaps
                Dim sOldPath As String = CStr(oSwap(2))
                Dim sNewPath As String = CStr(oSwap(3))
                Dim bSwapped As Boolean = False
                Try
                    For Each oFD As FileDescriptor In oDrawDoc.File.ReferencedFileDescriptors
                        Dim sFDPath As String = ""
                        Try : sFDPath = oFD.FullFileName : Catch : Continue For : End Try
                        If String.Compare(sFDPath, sOldPath, True) = 0 Then
                            oFD.ReplaceReference(sNewPath)
                            bSwapped = True
                            Exit For
                        End If
                    Next
                    If bSwapped Then
                        iSwapOk = iSwapOk + 1
                        Try : System.IO.File.AppendAllText(sLogFilePath, "DRAW-REF-OK: " & System.IO.Path.GetFileName(sDrawPath) & " | " & System.IO.Path.GetFileName(sOldPath) & " -> " & System.IO.Path.GetFileName(sNewPath) & vbCrLf) : Catch : End Try
                    Else
                        iSwapFail = iSwapFail + 1
                        oLog.Append(vbCrLf & "DRAW-REF-FAIL: " & System.IO.Path.GetFileName(sDrawPath) & " | " & System.IO.Path.GetFileName(sOldPath) & " : no matching FileDescriptor")
                        Try : System.IO.File.AppendAllText(sLogFilePath, "DRAW-REF-FAIL: " & sDrawPath & " | " & sOldPath & " : no matching FileDescriptor" & vbCrLf) : Catch : End Try
                    End If
                Catch exRep As Exception
                    iSwapFail = iSwapFail + 1
                    oLog.Append(vbCrLf & "DRAW-REF-FAIL: " & System.IO.Path.GetFileName(sDrawPath) & " | " & System.IO.Path.GetFileName(sOldPath) & " : " & exRep.Message)
                    Try : System.IO.File.AppendAllText(sLogFilePath, "DRAW-REF-FAIL: " & sDrawPath & " | " & sOldPath & " : " & exRep.Message & vbCrLf) : Catch : End Try
                End Try
            Next

            ' --- Phase B2: model state re-assertion (if flag set for this drawing) ---
            ' After ReplaceReference the new document is bound, but named model states
            ' (e.g. "Weldment", "LOD_Low") may not auto-bind to the new doc.
            ' We iterate every DrawingView and call ChangeModelState to re-assert.
            Dim sDwgBasename As String = System.IO.Path.GetFileName(sDrawPath)
            Dim bDoStateMatch As Boolean = False
            If oDrawingStateMatch IsNot Nothing Then
                oDrawingStateMatch.TryGetValue(sDwgBasename, bDoStateMatch)
            End If
            If bDoStateMatch AndAlso iSwapOk > 0 Then
                Try
                    For Each oSheet As Sheet In oDrawDoc.Sheets
                        For Each oView As DrawingView In oSheet.DrawingViews
                            Dim sStateName As String = ""
                            Try : sStateName = oView.ModelState : Catch : End Try
                            If Trim(sStateName) <> "" AndAlso String.Compare(sStateName, "Master", True) <> 0 Then
                                Try
                                    oView.ChangeModelState(sStateName)
                                    Try : System.IO.File.AppendAllText(sLogFilePath, "DRAW-STATE-OK: " & sDwgBasename & " view state re-asserted: " & sStateName & vbCrLf) : Catch : End Try
                                Catch exState As Exception
                                    oLog.Append(vbCrLf & "DRAW-STATE-WARN: " & sDwgBasename & " view '" & sStateName & "' re-assert failed: " & exState.Message)
                                    Try : System.IO.File.AppendAllText(sLogFilePath, "DRAW-STATE-WARN: " & sDwgBasename & " : " & sStateName & " : " & exState.Message & vbCrLf) : Catch : End Try
                                End Try
                            End If
                        Next
                    Next
                Catch exStateOuter As Exception
                    oLog.Append(vbCrLf & "DRAW-STATE-WARN: " & sDwgBasename & " state loop error: " & exStateOuter.Message)
                End Try
            ElseIf Not bDoStateMatch Then
                Try : System.IO.File.AppendAllText(sLogFilePath, "DRAW-STATE-SKIP: " & sDwgBasename & " (match model states not enabled)" & vbCrLf) : Catch : End Try
            End If

            ' --- Phase C: verify - check for any remaining old-path refs ---
            Dim bAllClean As Boolean = True
            For Each oRef As Document In oDrawDoc.ReferencedDocuments
                Dim sRefPath As String = ""
                Try : sRefPath = oRef.FullDocumentName : Catch : Continue For : End Try
                ' If this ref is in the rename map as a KEY (i.e. it's an old path), it wasn't updated
                If oRenameMap.ContainsKey(sRefPath) Then
                    bAllClean = False
                    oLog.Append(vbCrLf & "DRAW-UNRESOLVED-REMAIN: " & System.IO.Path.GetFileName(sDrawPath) & " still refs old: " & System.IO.Path.GetFileName(sRefPath))
                    Try : System.IO.File.AppendAllText(sLogFilePath, "DRAW-UNRESOLVED-REMAIN: " & sDrawPath & " still refs " & sRefPath & vbCrLf) : Catch : End Try
                End If
            Next

            ' --- Phase D: save only if fully clean ---
            If bAllClean AndAlso iSwapOk > 0 Then
                ' Clear read-only flag if present (Vault source files are RO)
                Try
                    Dim oAttrs As System.IO.FileAttributes = System.IO.File.GetAttributes(sDrawPath)
                    If (oAttrs And System.IO.FileAttributes.ReadOnly) = System.IO.FileAttributes.ReadOnly Then
                        System.IO.File.SetAttributes(sDrawPath, oAttrs And Not System.IO.FileAttributes.ReadOnly)
                    End If
                Catch
                End Try
                Try
                    oDrawDoc.Save()
                    iDwgOk = iDwgOk + 1
                    oLog.Append(vbCrLf & "DRAW-OK: " & System.IO.Path.GetFileName(sDrawPath) & " (" & iSwapOk & " ref(s) updated)")
                    Try : System.IO.File.AppendAllText(sLogFilePath, "DRAW-OK: " & sDrawPath & vbCrLf) : Catch : End Try
                Catch exSave As Exception
                    oLog.Append(vbCrLf & "DRAW-SAVE-FAIL: " & System.IO.Path.GetFileName(sDrawPath) & " : " & exSave.Message)
                    iDwgPartial = iDwgPartial + 1
                    Try : System.IO.File.AppendAllText(sLogFilePath, "DRAW-SAVE-FAIL: " & sDrawPath & " : " & exSave.Message & vbCrLf) : Catch : End Try
                End Try
            ElseIf iSwapOk = 0 AndAlso oSwaps.Count = 0 Then
                ' No refs in this drawing matched the rename map - nothing to do, not an error
                oLog.Append(vbCrLf & "DRAW-NOOP: " & System.IO.Path.GetFileName(sDrawPath) & " (no refs matched rename map)")
            Else
                ' Partial or unresolved - do NOT save
                iDwgPartial = iDwgPartial + 1
                oLog.Append(vbCrLf & "DRAW-PARTIAL-SKIP: " & System.IO.Path.GetFileName(sDrawPath) & " NOT saved (" & iSwapOk & " OK, " & iSwapFail & " fail) - manual repair required")
                Try : System.IO.File.AppendAllText(sLogFilePath, "DRAW-PARTIAL-SKIP: " & sDrawPath & vbCrLf) : Catch : End Try
            End If

        Catch exOuter As Exception
            iDwgFail = iDwgFail + 1
            oLog.Append(vbCrLf & "DRAW-OPEN-FAIL: " & System.IO.Path.GetFileName(sDrawPath) & " : " & exOuter.Message)
            Try : System.IO.File.AppendAllText(sLogFilePath, "DRAW-OPEN-FAIL: " & sDrawPath & " : " & exOuter.Message & vbCrLf) : Catch : End Try
        Finally
            ' Re-enable event-driven rules before closing (restores document state cleanly)
            If oDrawDoc IsNot Nothing Then
                Try : oDrawDoc.iLogicVb.EventRuleManager.DisableEventRules = False : Catch : End Try
            End If
            ' Always close the drawing after processing - it's not part of the model tree
            If oDrawDoc IsNot Nothing Then
                Try : oDrawDoc.Close(False) : Catch : End Try
                oDrawDoc = Nothing
            End If
        End Try

        ' Periodic GC to prevent memory balloon on large drawing sets
    Next

    ' ══════════════════════════════════════════════════════════════════════
    ' INTEGRITY + REPAIR PASS
    '
    ' Design contract:
    '   The GA drawing is the anchor. Every model a drawing references must
    '   exist in sTargetFolder AND be wired into the GA assembly tree.
    '   This pass enforces that via Component Replace — always, unconditionally.
    '
    ' Two-case repair (both end with Component Replace):
    '   Case A — expected-name file already in sTargetFolder
    '             → Replace occurrence with sTargetFolder copy. No SaveAs.
    '               Even if already correct — "foregone conclusion", re-cements link.
    '               Handles BOTH prefix-only renames (same basename) AND
    '               segment-renamed subs (GA still has old-segment name,
    '               e.g. E3432-8-TANK UPPER ASSEMBLY → 3450-001-V01-01).
    '   Case B — expected-name not in sTargetFolder, but source exists on disk
    '             → File.Copy to sTargetFolder, then Component Replace.
    '
    ' Step 1:  Build sTargetFolder file inventory (basename → fullPath)
    ' Step 1b: Build basename rename map from oRenameMap (oldBasename → newBasename)
    '          so segment-renamed subs in the GA tree are caught and replaced
    '          with their correctly-named counterparts.
    ' Step 2: Find new GA .iam; open it; walk Occurrences recursively;
    '         Component Replace each sub with its sTargetFolder counterpart.
    '         Log INTEGRITY-REPAIR or INTEGRITY-COPY-AND-REPAIR for each.
    '         Log INTEGRITY-WARN-MISSING if sub not findable anywhere.
    ' Step 3: Save GA.
    ' Step 4: Drawing stale-path check — verify each drawing ref's
    '         FullDocumentName starts with sTargetFolder. Report only.
    ' ══════════════════════════════════════════════════════════════════════
    Try : System.IO.File.AppendAllText(sLogFilePath, vbCrLf & "══ INTEGRITY + REPAIR PASS ═════════════════════════════════" & vbCrLf) : Catch : End Try

    Dim iIntRepair      As Integer = 0
    Dim iIntCopyRepair  As Integer = 0
    Dim iIntMissing     As Integer = 0
    Dim iIntStalePath   As Integer = 0
    Dim oIntMsgLines    As New System.Collections.Generic.List(Of String)

    If Trim(sTargetFolder) <> "" AndAlso System.IO.Directory.Exists(sTargetFolder) Then

        ' ── Step 1: Build target folder inventory (case-insensitive basename → full path) ──
        Dim oTargetInv As New System.Collections.Generic.Dictionary(Of String, String)(StringComparer.OrdinalIgnoreCase)
        Try
            For Each sInvFile As String In System.IO.Directory.GetFiles(sTargetFolder)
                Dim sInvBase As String = System.IO.Path.GetFileName(sInvFile)
                If Not oTargetInv.ContainsKey(sInvBase) Then oTargetInv(sInvBase) = sInvFile
            Next
        Catch : End Try
        Try : System.IO.File.AppendAllText(sLogFilePath, "INTEGRITY: target folder inventory — " & oTargetInv.Count & " file(s)" & vbCrLf) : Catch : End Try

        ' ── Step 1b: Build basename rename lookup from oRenameMap ──────────
        ' Critical for segment-renamed subs: the GA may still reference
        ' old-segment names (e.g. PJ00205-E3432-8-TANK UPPER ASSEMBLY.iam)
        ' while the target folder holds the segment-renamed version
        ' (e.g. PJ00205-3450-001-V01-01.iam).
        ' oRenameMap keys = old full paths; values = new full paths.
        ' This map lets the walk replace by NEW name, not old name.
        Dim oBasenameRenameMap As New System.Collections.Generic.Dictionary(Of String, String)(StringComparer.OrdinalIgnoreCase)
        For Each oRmKvp As System.Collections.Generic.KeyValuePair(Of String, String) In oRenameMap
            Dim sOldBase As String = System.IO.Path.GetFileName(oRmKvp.Key)
            Dim sNewBase As String = System.IO.Path.GetFileName(oRmKvp.Value)
            If Not oBasenameRenameMap.ContainsKey(sOldBase) Then
                oBasenameRenameMap(sOldBase) = sNewBase
            End If
        Next
        Try : System.IO.File.AppendAllText(sLogFilePath, "INTEGRITY: rename-map basename entries — " & oBasenameRenameMap.Count & vbCrLf) : Catch : End Try

        ' ── Step 2: Identify new GA .iam path ──────────────────────────────
        ' Strategy 1 (best): scan open Documents for a .iam already in sTargetFolder
        '   — works even when the active drawing is a title sheet with 0 model refs.
        ' Strategy 2: walk oRenameMap values for a .iam in sTargetFolder.
        ' Strategy 3: walk oRenameMap values for any .iam (broadest fallback).
        ' Strategy 4: scan open Documents for any .iam in the project parent tree.
        '
        ' Fix #7: single pass over ThisApplication.Documents cached here;
        '         Strategies 1, 4, and the GA-open check all reuse this cache.
        Dim oIntegOpenDocCache As New System.Collections.Generic.Dictionary(Of String, Document)(StringComparer.OrdinalIgnoreCase)
        Try
            For Each oCacheD As Document In ThisApplication.Documents
                Dim sCachePath As String = ""
                Try : sCachePath = oCacheD.FullFileName : Catch : Continue For : End Try
                If Trim(sCachePath) <> "" Then oIntegOpenDocCache(sCachePath) = oCacheD
            Next
        Catch : End Try

        Dim sNewGaPath As String = ""
        ' -- Strategy 1: open Documents in sTargetFolder (from cache) --
        Try
            Dim oIntegIamCandidates As New System.Collections.Generic.List(Of String)
            For Each sOpenFull As String In oIntegOpenDocCache.Keys
                If String.Compare(System.IO.Path.GetExtension(sOpenFull), ".iam", True) = 0 Then
                    If System.IO.Path.GetDirectoryName(sOpenFull).Equals(sTargetFolder, StringComparison.OrdinalIgnoreCase) Then
                        oIntegIamCandidates.Add(sOpenFull)
                    End If
                End If
            Next
            If oIntegIamCandidates.Count = 1 Then
                sNewGaPath = oIntegIamCandidates(0)
                Try : System.IO.File.AppendAllText(sLogFilePath, "INTEGRITY: GA found via open Documents in target folder → " & System.IO.Path.GetFileName(sNewGaPath) & vbCrLf) : Catch : End Try
            ElseIf oIntegIamCandidates.Count > 1 Then
                sNewGaPath = oIntegIamCandidates(0)
                Try : System.IO.File.AppendAllText(sLogFilePath, "INTEGRITY: multiple .iam open in target — using first: " & System.IO.Path.GetFileName(sNewGaPath) & vbCrLf) : Catch : End Try
            End If
        Catch : End Try
        ' -- Strategy 2 & 3: oRenameMap values --
        If Trim(sNewGaPath) = "" Then
            For Each sMapVal As String In oRenameMap.Values
                If String.Compare(System.IO.Path.GetExtension(sMapVal), ".iam", True) = 0 AndAlso _
                   System.IO.Path.GetDirectoryName(sMapVal).Equals(sTargetFolder, StringComparison.OrdinalIgnoreCase) Then
                    sNewGaPath = sMapVal : Exit For
                End If
            Next
        End If
        If Trim(sNewGaPath) = "" Then
            For Each sMapVal As String In oRenameMap.Values
                If String.Compare(System.IO.Path.GetExtension(sMapVal), ".iam", True) = 0 Then
                    sNewGaPath = sMapVal : Exit For
                End If
            Next
        End If
        ' -- Strategy 4: any open .iam in project parent tree (from cache) --
        If Trim(sNewGaPath) = "" Then
            Try
                Dim sProjParent As String = System.IO.Path.GetDirectoryName(sTargetFolder.TrimEnd(System.IO.Path.DirectorySeparatorChar))
                For Each sOpenFull As String In oIntegOpenDocCache.Keys
                    If String.Compare(System.IO.Path.GetExtension(sOpenFull), ".iam", True) = 0 Then
                        If System.IO.Path.GetDirectoryName(sOpenFull).StartsWith(sProjParent, StringComparison.OrdinalIgnoreCase) Then
                            sNewGaPath = sOpenFull : Exit For
                        End If
                    End If
                Next
                If Trim(sNewGaPath) <> "" Then
                    Try : System.IO.File.AppendAllText(sLogFilePath, "INTEGRITY: GA found via open Documents (project tree) → " & System.IO.Path.GetFileName(sNewGaPath) & vbCrLf) : Catch : End Try
                End If
            Catch : End Try
        End If

        If Trim(sNewGaPath) <> "" AndAlso System.IO.File.Exists(sNewGaPath) Then
            Try : System.IO.File.AppendAllText(sLogFilePath, "INTEGRITY: GA assembly → " & System.IO.Path.GetFileName(sNewGaPath) & vbCrLf) : Catch : End Try

            ' ── Step 2 cont.: Open GA + recursive Component Replace walk ──
            Dim bWasIntegSilent As Boolean = ThisApplication.SilentOperation
            ThisApplication.SilentOperation = True
            Dim oGaDoc As AssemblyDocument = Nothing
            Dim bGaWasOpen As Boolean = False
            Try
                ' Check if already open — reuse cached open-doc scan (Fix #7)
                Dim oCachedGa As Document = Nothing
                If oIntegOpenDocCache.TryGetValue(sNewGaPath, oCachedGa) Then
                    oGaDoc = TryCast(oCachedGa, AssemblyDocument)
                    bGaWasOpen = True
                End If
                If oGaDoc Is Nothing Then
                    oGaDoc = TryCast(ThisApplication.Documents.Open(sNewGaPath, False), AssemblyDocument)
                End If
            Catch exGaOpen As Exception
                Try : System.IO.File.AppendAllText(sLogFilePath, "INTEGRITY-GA-OPEN-FAIL: " & exGaOpen.Message & vbCrLf) : Catch : End Try
            End Try

            If oGaDoc IsNot Nothing Then
                ' Recursive walker — replaces occurrences at every level
                Dim oIntegVisited As New System.Collections.Generic.HashSet(Of String)(StringComparer.OrdinalIgnoreCase)

                Dim WalkAndReplace As Action(Of AssemblyComponentDefinition) = Nothing
                WalkAndReplace = Sub(oDef As AssemblyComponentDefinition)
                    Try
                        For Each oOcc As ComponentOccurrence In oDef.Occurrences
                            Dim sOccPath As String = ""
                            Try : sOccPath = oOcc.ReferencedDocumentDescriptor.FullDocumentName : Catch : Continue For : End Try
                            If Trim(sOccPath) = "" OrElse oIntegVisited.Contains(sOccPath) Then Continue For
                            oIntegVisited.Add(sOccPath)

                            Dim sOccFileName As String = System.IO.Path.GetFileName(sOccPath)

                            ' ── Rename-map lookup: if this sub was segment-renamed,
                            '    use the NEW basename so we target the correct file in
                            '    sTargetFolder (e.g. E3432-8-TANK UPPER ASSEMBLY →
                            '    3450-001-V01-01). Falls back to same basename if no
                            '    mapping exists (prefix-only renames, already-correct subs).
                            Dim sExpectedFileName As String = sOccFileName
                            Dim sMappedBase As String = ""
                            If oBasenameRenameMap.TryGetValue(sOccFileName, sMappedBase) AndAlso _
                               Not String.Equals(sOccFileName, sMappedBase, StringComparison.OrdinalIgnoreCase) Then
                                sExpectedFileName = sMappedBase
                                Try : System.IO.File.AppendAllText(sLogFilePath, "INTEGRITY-SEGMENT-MAP: " & sOccFileName & " → " & sExpectedFileName & vbCrLf) : Catch : End Try
                            End If
                            Dim sOccExpected As String = System.IO.Path.Combine(sTargetFolder, sExpectedFileName)

                            If oTargetInv.ContainsKey(sExpectedFileName) Then
                                ' Case A: target-named file already in target folder — Component Replace (unconditional)
                                ' Handles both: same-name-different-folder AND segment-renamed subs in GA
                                If Not String.Equals(sOccPath, sOccExpected, StringComparison.OrdinalIgnoreCase) Then
                                    Try
                                        oOcc.Replace(sOccExpected, True)
                                        iIntRepair += 1
                                        Try : System.IO.File.AppendAllText(sLogFilePath, "INTEGRITY-REPAIR: " & sOccFileName & " → " & sExpectedFileName & vbCrLf) : Catch : End Try
                                    Catch exRep As Exception
                                        Try : System.IO.File.AppendAllText(sLogFilePath, "INTEGRITY-REPLACE-FAIL: " & sOccFileName & " → " & sExpectedFileName & " : " & exRep.Message & vbCrLf) : Catch : End Try
                                    End Try
                                Else
                                    ' Already pointing to correct target file — still replace to re-cement link
                                    Try
                                        oOcc.Replace(sOccExpected, True)
                                        iIntRepair += 1
                                        Try : System.IO.File.AppendAllText(sLogFilePath, "INTEGRITY-RELINK: " & sOccFileName & " (already in target — re-cemented)" & vbCrLf) : Catch : End Try
                                    Catch : End Try
                                End If
                            ElseIf System.IO.File.Exists(sOccPath) Then
                                ' Case B: expected-name not in target folder, but source exists — copy then Replace
                                Try
                                    System.IO.File.Copy(sOccPath, sOccExpected, True)
                                    oOcc.Replace(sOccExpected, True)
                                    oTargetInv(sExpectedFileName) = sOccExpected   ' update inventory
                                    iIntCopyRepair += 1
                                    Try : System.IO.File.AppendAllText(sLogFilePath, "INTEGRITY-COPY-AND-REPAIR: " & sExpectedFileName & " ← " & sOccPath & vbCrLf) : Catch : End Try
                                Catch exCopy As Exception
                                    Try : System.IO.File.AppendAllText(sLogFilePath, "INTEGRITY-COPY-FAIL: " & sExpectedFileName & " : " & exCopy.Message & vbCrLf) : Catch : End Try
                                End Try
                            ElseIf Not oBasenameRenameMap.ContainsKey(sOccFileName) Then
                                ' Case C — COPY-AS-IS: sub not in rename map at all (GA direct child
                                ' never referenced by any drawing — old-segment-style name).
                                ' Copy it to target folder under its original basename and re-wire.
                                ' This lands the file in the target folder for now; user can remap it
                                ' via the GA-Tree-First form extension in a future pass.
                                Dim sAsIsTarget As String = System.IO.Path.Combine(sTargetFolder, sOccFileName)
                                Dim sSourceSearch As String = sOccPath   ' already confirmed not on disk above
                                ' Try to find source in sibling folders relative to target
                                Dim sSibParent As String = System.IO.Path.GetDirectoryName(sTargetFolder.TrimEnd(System.IO.Path.DirectorySeparatorChar))
                                Dim sFoundSource As String = ""
                                If System.IO.File.Exists(sOccPath) Then
                                    sFoundSource = sOccPath
                                Else
                                    ' Search all open Documents for this filename
                                    Try
                                        For Each oOpenSearch As Document In ThisApplication.Documents
                                            Dim sSearchPath As String = ""
                                            Try : sSearchPath = oOpenSearch.FullFileName : Catch : Continue For : End Try
                                            If String.Equals(System.IO.Path.GetFileName(sSearchPath), sOccFileName, StringComparison.OrdinalIgnoreCase) Then
                                                sFoundSource = sSearchPath : Exit For
                                            End If
                                        Next
                                    Catch : End Try
                                End If
                                If Trim(sFoundSource) <> "" AndAlso System.IO.File.Exists(sFoundSource) Then
                                    Try
                                        System.IO.File.Copy(sFoundSource, sAsIsTarget, True)
                                        oOcc.Replace(sAsIsTarget, True)
                                        oTargetInv(sOccFileName) = sAsIsTarget   ' update inventory
                                        iIntCopyRepair += 1
                                        Try : System.IO.File.AppendAllText(sLogFilePath, "INTEGRITY-COPY-AS-IS: " & sOccFileName & " ← " & sFoundSource & vbCrLf) : Catch : End Try
                                    Catch exAsIs As Exception
                                        iIntMissing += 1
                                        Dim sAsIsFailLine As String = "INTEGRITY-COPY-AS-IS-FAIL: " & sOccFileName & " : " & exAsIs.Message
                                        oIntMsgLines.Add(sAsIsFailLine)
                                        Try : System.IO.File.AppendAllText(sLogFilePath, sAsIsFailLine & vbCrLf) : Catch : End Try
                                    End Try
                                Else
                                    ' Source file not found anywhere — geometry gap
                                    iIntMissing += 1
                                    Dim sMissAsIsLine As String = "INTEGRITY-WARN-MISSING: " & sOccFileName & " (not in rename map, source not found) — NOT FOUND anywhere"
                                    oIntMsgLines.Add(sMissAsIsLine)
                                    Try : System.IO.File.AppendAllText(sLogFilePath, sMissAsIsLine & vbCrLf) : Catch : End Try
                                End If
                            Else
                                ' Neither in target folder nor on disk — geometry gap
                                iIntMissing += 1
                                Dim sMissLine As String = "INTEGRITY-WARN-MISSING: " & sOccFileName & " (expected: " & sExpectedFileName & ") — NOT FOUND anywhere"
                                oIntMsgLines.Add(sMissLine)
                                Try : System.IO.File.AppendAllText(sLogFilePath, sMissLine & vbCrLf) : Catch : End Try
                            End If

                            ' Recurse into sub-assemblies
                            Try
                                Dim oSubDef As AssemblyComponentDefinition = _
                                    TryCast(oOcc.Definition, AssemblyComponentDefinition)
                                If oSubDef IsNot Nothing Then WalkAndReplace(oSubDef)
                            Catch : End Try
                        Next
                    Catch exWalk As Exception
                        Try : System.IO.File.AppendAllText(sLogFilePath, "INTEGRITY-WALK-ERR: " & exWalk.Message & vbCrLf) : Catch : End Try
                    End Try
                End Sub

                Try
                    WalkAndReplace(oGaDoc.ComponentDefinition)
                Catch exWalkRoot As Exception
                    Try : System.IO.File.AppendAllText(sLogFilePath, "INTEGRITY-WALK-ROOT-ERR: " & exWalkRoot.Message & vbCrLf) : Catch : End Try
                End Try

                ' ── Step 3: Save GA ────────────────────────────────────────
                Try
                    oGaDoc.Save()
                    Try : System.IO.File.AppendAllText(sLogFilePath, "INTEGRITY: GA saved OK" & vbCrLf) : Catch : End Try
                Catch exSave As Exception
                    Try : System.IO.File.AppendAllText(sLogFilePath, "INTEGRITY-GA-SAVE-FAIL: " & exSave.Message & vbCrLf) : Catch : End Try
                End Try

                If Not bGaWasOpen Then : Try : oGaDoc.Close(False) : Catch : End Try : End If
            End If
            ThisApplication.SilentOperation = bWasIntegSilent
        Else
            Try : System.IO.File.AppendAllText(sLogFilePath, "INTEGRITY: GA .iam not identified — skipping GA tree repair" & vbCrLf) : Catch : End Try
        End If

        ' ── Step 4: Drawing stale-path check (report only) ─────────────
        If Trim(sDwgFolder) <> "" AndAlso System.IO.Directory.Exists(sDwgFolder) Then
            Try : System.IO.File.AppendAllText(sLogFilePath, "INTEGRITY: checking drawing ref paths..." & vbCrLf) : Catch : End Try
            Dim oChkDwgFiles As New System.Collections.Generic.List(Of String)
            Try
                oChkDwgFiles.AddRange(System.IO.Directory.GetFiles(sDwgFolder, "*.dwg"))
                oChkDwgFiles.AddRange(System.IO.Directory.GetFiles(sDwgFolder, "*.idw"))
                oChkDwgFiles.Sort()
            Catch : End Try

            Dim bWasChkSilent As Boolean = ThisApplication.SilentOperation
            ThisApplication.SilentOperation = True
            For Each sChkDwg As String In oChkDwgFiles
                Dim oChkDwgDoc As DrawingDocument = Nothing
                Try
                    oChkDwgDoc = TryCast(ThisApplication.Documents.Open(sChkDwg, False), DrawingDocument)
                    If oChkDwgDoc Is Nothing Then Continue For
                    For Each oChkRef As Document In oChkDwgDoc.ReferencedDocuments
                        Dim sChkRefFull As String = ""
                        Try : sChkRefFull = oChkRef.FullDocumentName : Catch : Continue For : End Try
                        If Not sChkRefFull.StartsWith(sTargetFolder, StringComparison.OrdinalIgnoreCase) Then
                            iIntStalePath += 1
                            Dim sStaleLine As String = "INTEGRITY-WARN-STALE-PATH: " & System.IO.Path.GetFileName(sChkDwg) & _
                                                       " still refs " & sChkRefFull
                            oIntMsgLines.Add(sStaleLine)
                            Try : System.IO.File.AppendAllText(sLogFilePath, sStaleLine & vbCrLf) : Catch : End Try
                        End If
                    Next
                Catch exChk As Exception
                    Try : System.IO.File.AppendAllText(sLogFilePath, "INTEGRITY-DWG-OPEN-FAIL: " & System.IO.Path.GetFileName(sChkDwg) & " : " & exChk.Message & vbCrLf) : Catch : End Try
                Finally
                    If oChkDwgDoc IsNot Nothing Then : Try : oChkDwgDoc.Close(False) : Catch : End Try : End If
                End Try
            Next
            ThisApplication.SilentOperation = bWasChkSilent
        End If

    End If

    ' ── Summary + popup ────────────────────────────────────────────────
    Try : System.IO.File.AppendAllText(sLogFilePath, _
        "INTEGRITY SUMMARY: " & iIntRepair & " relinked, " & iIntCopyRepair & " copy-repaired/as-is, " & _
        iIntMissing & " MISSING, " & iIntStalePath & " stale-drawing-paths" & vbCrLf) : Catch : End Try

    If iIntMissing > 0 OrElse iIntStalePath > 0 Then
        Dim sSummMsg As String = "INTEGRITY WARNINGS" & vbCrLf & vbCrLf
        If iIntMissing > 0 Then sSummMsg &= "⚠ " & iIntMissing & " sub(s) not found anywhere — geometry gap risk" & vbCrLf
        If iIntStalePath > 0 Then sSummMsg &= "⚠ " & iIntStalePath & " drawing ref(s) still point outside the target folder" & vbCrLf
        sSummMsg &= vbCrLf & String.Join(vbCrLf, oIntMsgLines.GetRange(0, Math.Min(15, oIntMsgLines.Count)))
        If oIntMsgLines.Count > 15 Then sSummMsg &= vbCrLf & "... (see log for full list)"
        sSummMsg &= vbCrLf & vbCrLf & "See log on Desktop for details."
        MessageBox.Show(sSummMsg, "Integrity Check — Action Required", MessageBoxButtons.OK, MessageBoxIcon.Warning)
    ElseIf iIntRepair + iIntCopyRepair > 0 Then
        Try : System.IO.File.AppendAllText(sLogFilePath, "INTEGRITY: all refs repaired and re-cemented into GA tree." & vbCrLf) : Catch : End Try
    End If

    ' ── DRAWING REFS REPORT — rename-map match annotation ─────────────────
    ' Append to the report file created earlier: for each drawing ref, show
    ' whether oRenameMap has a new name for it (MATCHED) or not (NO-MATCH).
    Try
        Dim sbDwgRefsAnnot As New System.Text.StringBuilder()
        sbDwgRefsAnnot.AppendLine()
        sbDwgRefsAnnot.AppendLine(New String("="c, 120))
        sbDwgRefsAnnot.AppendLine("RENAME-MAP MATCH STATUS  (annotated at end of run)")
        sbDwgRefsAnnot.AppendLine("Generated: " & DateTime.Now.ToString())
        sbDwgRefsAnnot.AppendLine(New String("="c, 120))
        sbDwgRefsAnnot.AppendLine()
        For Each oKvpDwg As System.Collections.Generic.KeyValuePair(Of String, System.Collections.Generic.List(Of String)) In oAllDwgRefs
            sbDwgRefsAnnot.AppendLine("DWG: " & System.IO.Path.GetFileName(oKvpDwg.Key))
            For Each sRefItem As String In oKvpDwg.Value
                Dim sNewName As String = ""
                Dim sMatchTag As String = If(oRenameMap.TryGetValue(sRefItem, sNewName), _
                    "  MATCHED  → " & System.IO.Path.GetFileName(sNewName), _
                    "  NO-MATCH (no rename entry)")
                sbDwgRefsAnnot.AppendLine("   " & System.IO.Path.GetFileName(sRefItem) & sMatchTag)
            Next
            If oKvpDwg.Value.Count = 0 Then sbDwgRefsAnnot.AppendLine("   (no model refs resolved)")
            sbDwgRefsAnnot.AppendLine()
        Next
        System.IO.File.AppendAllText(sDwgRefsDesktop, sbDwgRefsAnnot.ToString())
        System.IO.File.AppendAllText(sDwgRefsDwgFolder, sbDwgRefsAnnot.ToString())
    Catch exAnnot As Exception
        Try : System.IO.File.AppendAllText(sLogFilePath, "DRAWING-REFS-ANNOT-FAIL: " & exAnnot.Message & vbCrLf) : Catch : End Try
    End Try

    ' ── POST-RULE TREE GRAB ────────────────────────────────────────────────
    ' Captures the GA tree after all operations + integrity pass.
    ' Diff PRE vs POST in Notepad++ Compare to see exactly what moved.
    Dim sPostTreeDesktop As String = System.Environment.GetFolderPath(System.Environment.SpecialFolder.Desktop) & "\POST_Tree_" & sRunStamp & ".txt"
    Dim sPostTreeDwgFolder As String = System.IO.Path.Combine(sDwgFolder, "POST_Tree_" & sRunStamp & ".txt")
    Try
        Dim sPostGaPath As String = ""
        ' Use oRenameMap to find the new GA path (same logic as integrity pass Step 2)
        For Each sOldRef As String In oScanRefs
            Dim sMappedGa As String = ""
            If oRenameMap.TryGetValue(sOldRef, sMappedGa) AndAlso _
               String.Compare(System.IO.Path.GetExtension(sMappedGa), ".iam", True) = 0 Then
                sPostGaPath = sMappedGa : Exit For
            End If
        Next
        If Trim(sPostGaPath) = "" Then
            For Each sOldRef As String In oScanRefs
                If String.Compare(System.IO.Path.GetExtension(sOldRef), ".iam", True) = 0 AndAlso _
                   System.IO.File.Exists(System.IO.Path.Combine(sTargetFolder, System.IO.Path.GetFileName(sOldRef))) Then
                    sPostGaPath = System.IO.Path.Combine(sTargetFolder, System.IO.Path.GetFileName(sOldRef)) : Exit For
                End If
            Next
        End If
        If Trim(sPostGaPath) <> "" AndAlso System.IO.File.Exists(sPostGaPath) Then
            Dim sPostHeader As String = "POST-RULE ASSEMBLY TREE SNAPSHOT" & vbCrLf & _
                "Generated: " & DateTime.Now.ToString() & vbCrLf & _
                "Assembly: " & sPostGaPath & vbCrLf & _
                New String("="c, 120) & vbCrLf & vbCrLf
            System.IO.File.WriteAllText(sPostTreeDesktop, sPostHeader)
            System.IO.File.WriteAllText(sPostTreeDwgFolder, sPostHeader)
            Dim oPostGaDoc As AssemblyDocument = Nothing
            Dim bPostWasOpen As Boolean = False
            Try
                For Each oOpenD As Document In ThisApplication.Documents
                    If String.Equals(oOpenD.FullFileName, sPostGaPath, StringComparison.OrdinalIgnoreCase) Then
                        oPostGaDoc = TryCast(oOpenD, AssemblyDocument)
                        bPostWasOpen = True : Exit For
                    End If
                Next
                If oPostGaDoc Is Nothing Then
                    oPostGaDoc = TryCast(ThisApplication.Documents.Open(sPostGaPath, False), AssemblyDocument)
                End If
            Catch : End Try
            If oPostGaDoc IsNot Nothing Then
                Dim iPostCount As Integer = 0
                WalkTreeToLog(oPostGaDoc.ComponentDefinition.Occurrences, 0, sPostTreeDesktop, iPostCount)
                WalkTreeToLog(oPostGaDoc.ComponentDefinition.Occurrences, 0, sPostTreeDwgFolder, iPostCount)
                Dim sPostFooter As String = vbCrLf & New String("="c, 120) & vbCrLf & "Total occurrences listed: " & iPostCount & vbCrLf
                System.IO.File.AppendAllText(sPostTreeDesktop, sPostFooter)
                System.IO.File.AppendAllText(sPostTreeDwgFolder, sPostFooter)
                If Not bPostWasOpen Then Try : oPostGaDoc.Close(False) : Catch : End Try
                Try : System.IO.File.AppendAllText(sLogFilePath, "POST-TREE: " & iPostCount & " occurrence(s) captured → " & System.IO.Path.GetFileName(sPostTreeDwgFolder) & vbCrLf) : Catch : End Try
            End If
        Else
            Try : System.IO.File.AppendAllText(sLogFilePath, "POST-TREE: GA path not resolved — skipped" & vbCrLf) : Catch : End Try
        End If
    Catch exPost As Exception
        Try : System.IO.File.AppendAllText(sLogFilePath, "POST-TREE-FAIL: " & exPost.Message & vbCrLf) : Catch : End Try
    End Try

    ' ── Write RunLog [ORIGINAL_*] (Pass 1 only) + [SUMMARY] ──────────────
    Try
        Dim sbRunLogClose As New System.Text.StringBuilder()
        ' ORIGINAL blocks — written ONLY on Pass 1, never overwritten
        If bIsOriginPass Then
            sbRunLogClose.AppendLine("[ORIGINAL_GA_TREE]")
            ' Re-read the PRE-TREE file if it exists
            Try
                If System.IO.File.Exists(sPreTreeDwgFolder) Then
                    Dim sPreContent As String = System.IO.File.ReadAllText(sPreTreeDwgFolder)
                    sbRunLogClose.AppendLine(sPreContent)
                Else
                    sbRunLogClose.AppendLine("(pre-tree file not found — GA may not have been open)")
                End If
            Catch : sbRunLogClose.AppendLine("(pre-tree read failed)") : End Try
            sbRunLogClose.AppendLine()
            sbRunLogClose.AppendLine("[ORIGINAL_DRAWING_LIST]")
            For Each sOrigDwgPath As String In oAllDwgPaths
                sbRunLogClose.AppendLine(System.IO.Path.GetFileName(sOrigDwgPath))
            Next
            sbRunLogClose.AppendLine()
            sbRunLogClose.AppendLine("[ORIGINAL_DRAWING_REFS]")
            For Each oKvpOrig As System.Collections.Generic.KeyValuePair(Of String, System.Collections.Generic.List(Of String)) In oAllDwgRefs
                For Each sOrigRef As String In oKvpOrig.Value
                    sbRunLogClose.AppendLine(System.IO.Path.GetFileName(oKvpOrig.Key) & " = " & sOrigRef)
                Next
            Next
            sbRunLogClose.AppendLine()
        End If
        ' [SUMMARY] — every pass
        sbRunLogClose.AppendLine("[SUMMARY]")
        sbRunLogClose.AppendLine("pass = " & iRunPass)
        sbRunLogClose.AppendLine("timestamp = " & sRunStamp)
        sbRunLogClose.AppendLine("rename_map_entries = " & oRenameMap.Count)
        sbRunLogClose.AppendLine("integrity_relinked = " & iIntRepair)
        sbRunLogClose.AppendLine("integrity_copy_repaired = " & iIntCopyRepair)
        sbRunLogClose.AppendLine("integrity_missing = " & iIntMissing)
        sbRunLogClose.AppendLine("integrity_stale_paths = " & iIntStalePath)
        sbRunLogClose.AppendLine()
        System.IO.File.AppendAllText(sRunLogPath, sbRunLogClose.ToString())
        Try : System.IO.File.AppendAllText(sLogFilePath, "RUN-LOG: pass " & iRunPass & " closed → " & System.IO.Path.GetFileName(sRunLogPath) & vbCrLf) : Catch : End Try
    Catch exRunLogClose As Exception
        Try : System.IO.File.AppendAllText(sLogFilePath, "RUN-LOG-CLOSE-FAIL: " & exRunLogClose.Message & vbCrLf) : Catch : End Try
    End Try

    ' ── COPY MAIN LOG TO DRAWINGS FOLDER ──────────────────────────────────
    ' Desktop log stays for quick access. Drawings folder copy is the
    ' permanent project record alongside PRE/POST trees and DrawingRefs.
    Try
        Dim sDwgFolderLog As String = System.IO.Path.Combine(sDwgFolder, "DrawingCopyMode_Log_" & sRunStamp & ".txt")
        System.IO.File.Copy(sLogFilePath, sDwgFolderLog, True)
        Try : System.IO.File.AppendAllText(sLogFilePath, "LOG-COPY: archived to drawings folder → " & System.IO.Path.GetFileName(sDwgFolderLog) & vbCrLf) : Catch : End Try
    Catch exLogCopy As Exception
        Try : System.IO.File.AppendAllText(sLogFilePath, "LOG-COPY-FAIL: " & exLogCopy.Message & vbCrLf) : Catch : End Try
    End Try

    ThisApplication.SilentOperation = bOrigSilent

End Sub


' =====================================================================
' PHASE 0: DRAWING SCAN
' =====================================================================
' Scans sDrawingsFolder (flat) and returns a structure describing which
' drawings reference which model files.
' Return: List of (sDrawingBasename, List(Of sModelBasename)) pairs.
' Both keys are basenames WITHOUT extension for model, WITH extension for drawing.
' SilentOperation must be set by caller.
' =====================================================================
Function RunPhase0DrawingScan(sDrawingsFolder As String, oLog As System.Text.StringBuilder, sLogFilePath As String) _
    As System.Collections.Generic.List(Of Object())
    ' Each Object() = { sDrawingBasename As String, List(Of String) modelBasenames }

    Dim oResult As New System.Collections.Generic.List(Of Object())

    ' Collect both Inventor native (.idw) and Inventor DWG (.dwg) drawing files.
    Dim oIdwFiles As New System.Collections.Generic.List(Of String)
    Try
        oIdwFiles.AddRange(System.IO.Directory.GetFiles(sDrawingsFolder, "*.idw"))
        oIdwFiles.AddRange(System.IO.Directory.GetFiles(sDrawingsFolder, "*.dwg"))
        oIdwFiles.Sort()   ' consistent order
    Catch ex As Exception
        oLog.Append(vbCrLf & "PHASE0: could not read drawings folder: " & ex.Message)
        Return oResult
    End Try

    For Each sIdwPath As String In oIdwFiles
        Dim sDwgBasename As String = System.IO.Path.GetFileName(sIdwPath)
        Dim oModelList As New System.Collections.Generic.List(Of String)
        Dim oDwgDoc As DrawingDocument = Nothing
        Try
            oDwgDoc = TryCast(ThisApplication.Documents.Open(sIdwPath, False), DrawingDocument)
            If oDwgDoc IsNot Nothing Then
                For Each oRef As Document In oDwgDoc.ReferencedDocuments
                    Dim sRefBasename As String = ""
                    Try : sRefBasename = System.IO.Path.GetFileNameWithoutExtension(oRef.FullDocumentName) : Catch : Continue For : End Try
                    If sRefBasename <> "" AndAlso Not oModelList.Contains(sRefBasename) Then
                        oModelList.Add(sRefBasename)
                    End If
                Next
            End If
        Catch ex As Exception
            oLog.Append(vbCrLf & "PHASE0-OPEN-FAIL: " & sDwgBasename & " : " & ex.Message)
            Try : System.IO.File.AppendAllText(sLogFilePath, "PHASE0-OPEN-FAIL: " & sIdwPath & " : " & ex.Message & vbCrLf) : Catch : End Try
        Finally
            If oDwgDoc IsNot Nothing Then
                Try : oDwgDoc.Close(False) : Catch : End Try
            End If
        End Try

        If oModelList.Count > 0 Then
            oResult.Add(New Object() {sDwgBasename, oModelList})
        End If
    Next

    Return oResult
End Function


' =====================================================================
' DRAWING MODEL RENAME FORM
' =====================================================================
' Shows a scrollable form with one group per drawing, one row per unique
' model referenced by that drawing.
'
' LEFT COLUMN  = old model basename (read-only, grey)
' RIGHT COLUMN = new model basename (editable on FIRST appearance of that
'                model; grey/locked on all subsequent appearances because
'                the same old name can only map to one new name)
'
' Per-drawing "Match model states?" checkbox (default ticked).
' Global checkbox at bottom controls all per-drawing ones simultaneously.
'
' Returns True if user clicked OK, False if cancelled.
' oChoice.oExplicitModelRenameMap is populated on OK.
' oChoice.oDrawingStateMatch is populated on OK.
' =====================================================================
' ShowGaSelectionDialog
' Shows a radio-button dialog when the active GA drawing references more
' than one .iam assembly. The user nominates which is the principal GA.
' Returns the full path of the selected .iam, or "" if cancelled.
' OK is disabled until exactly one radio button is selected.
' =====================================================================
Function ShowGaSelectionDialog( _
    oIamPaths As System.Collections.Generic.List(Of String), _
    sDrawingPath As String) As String

    Dim oForm As New System.Windows.Forms.Form()
    oForm.Text = "Select Principal GA Assembly"
    oForm.Width = 560
    oForm.Height = 0   ' calculated below
    oForm.StartPosition = System.Windows.Forms.FormStartPosition.CenterScreen
    oForm.FormBorderStyle = System.Windows.Forms.FormBorderStyle.FixedDialog
    oForm.MaximizeBox = False
    oForm.MinimizeBox = False

    ' Instruction label
    Dim oLblInstruct As New System.Windows.Forms.Label()
    oLblInstruct.Text = "This drawing references more than one assembly. Select the PRINCIPAL GA Assembly." & vbCrLf & _
                        "Secondary assemblies (reference models) will be copied as-is — they will not drive the tree walk."
    oLblInstruct.Left = 10 : oLblInstruct.Top = 10 : oLblInstruct.Width = 520 : oLblInstruct.Height = 44
    oForm.Controls.Add(oLblInstruct)

    Dim oLblDwg As New System.Windows.Forms.Label()
    oLblDwg.Text = "Drawing: " & System.IO.Path.GetFileName(sDrawingPath)
    oLblDwg.Left = 10 : oLblDwg.Top = 56 : oLblDwg.Width = 520 : oLblDwg.Height = 20
    oForm.Controls.Add(oLblDwg)

    ' One RadioButton per .iam ref
    Dim oRadios As New System.Collections.Generic.List(Of System.Windows.Forms.RadioButton)()
    Dim iY As Integer = 86
    For Each sIamPath As String In oIamPaths
        Dim oRad As New System.Windows.Forms.RadioButton()
        oRad.Text = System.IO.Path.GetFileName(sIamPath)
        oRad.Tag = sIamPath
        oRad.Left = 20 : oRad.Top = iY : oRad.Width = 500 : oRad.Height = 24
        oRad.Checked = False
        oForm.Controls.Add(oRad)
        oRadios.Add(oRad)
        iY = iY + 28
    Next

    ' Separator note
    Dim oLblNote As New System.Windows.Forms.Label()
    oLblNote.Text = "Only one assembly can be the principal GA. You cannot proceed until one is selected."
    oLblNote.Left = 10 : oLblNote.Top = iY + 6 : oLblNote.Width = 520 : oLblNote.Height = 20
    oForm.Controls.Add(oLblNote)

    ' OK / Cancel — right-aligned, no overlap.
    ' Form client width ≈ 544px (560 outer − 16 border).
    ' Cancel: right-flush at 534.  OK: 12px gap to its left.
    Dim iFootTop As Integer = iY + 32
    Dim oCancel As New System.Windows.Forms.Button()
    oCancel.Text = "Cancel"
    oCancel.DialogResult = System.Windows.Forms.DialogResult.Cancel
    oCancel.Left = 454 : oCancel.Top = iFootTop : oCancel.Width = 80
    oForm.Controls.Add(oCancel) : oForm.CancelButton = oCancel

    Dim oOk As New System.Windows.Forms.Button()
    oOk.Text = "OK — Use Selected as GA"
    oOk.Left = 262 : oOk.Top = iFootTop : oOk.Width = 182
    oOk.Enabled = False   ' disabled until a radio button is ticked
    oForm.Controls.Add(oOk) : oForm.AcceptButton = oOk

    ' +80 gives button (≈26px) + bottom padding + Windows chrome clearance.
    ' Previous +60 clipped the button row at high DPI.
    oForm.Height = iFootTop + 80

    ' Enable OK when any radio is selected.
    ' NOTE: For Each inside a lambda is not supported by the iLogic compiler —
    '       use the sender directly instead. RadioButtons are mutually exclusive,
    '       so OK fires enabled on the first Checked=True and stays enabled.
    For Each oRad As Object In oRadios
        AddHandler CType(oRad, System.Windows.Forms.RadioButton).CheckedChanged, Sub(s, e)
            If CType(s, System.Windows.Forms.RadioButton).Checked Then oOk.Enabled = True
        End Sub
    Next

    AddHandler oOk.Click, Sub(s, e)
        oForm.DialogResult = System.Windows.Forms.DialogResult.OK
        oForm.Close()
    End Sub

    If oForm.ShowDialog() <> System.Windows.Forms.DialogResult.OK Then Return ""

    ' Return the path from the selected radio button
    For Each oRad As Object In oRadios
        If CType(oRad, System.Windows.Forms.RadioButton).Checked Then
            Return CStr(CType(oRad, System.Windows.Forms.RadioButton).Tag)
        End If
    Next
    Return ""
End Function


' =====================================================================
Function ShowDrawingModelRenameForm( _
    ByRef oChoice As RenameModeChoice, _
    oPhase0Data As System.Collections.Generic.List(Of Object())) As Boolean

    If oPhase0Data Is Nothing OrElse oPhase0Data.Count = 0 Then
        ' No drawings found - nothing to show; self-map will be empty which is fine
        Return True
    End If

    ' Master map: old model basename -> TextBox holding new name (shared across groups)
    Dim oMasterTxtMap As New System.Collections.Generic.Dictionary(Of String, System.Windows.Forms.TextBox)(StringComparer.OrdinalIgnoreCase)
    ' Per-drawing include checkboxes (left side of each header — controls pre-tick in selection form)
    Dim oIncludeCheckMap As New System.Collections.Generic.Dictionary(Of String, CheckBox)(StringComparer.OrdinalIgnoreCase)
    ' Per-drawing state-match checkboxes (right side of each header)
    Dim oStateCheckMap As New System.Collections.Generic.Dictionary(Of String, CheckBox)(StringComparer.OrdinalIgnoreCase)

    ' Layout constants
    Const iFormW As Integer = 680
    Const iPanelLeft As Integer = 10
    Const iPanelW As Integer = 648    ' form client - 2*margin
    ' Field columns (relative to panel content, accounting for 6px left pad)
    Const iOldLeft As Integer = 6
    Const iOldW As Integer = 268
    Const iArrLeft As Integer = 277
    Const iNewLeft As Integer = 300
    Const iNewW As Integer = 336

    ' ---- Build the form ----
    Dim oForm As New Form()
    oForm.Text = "Drawing Model Renames — Step 2 of 3"
    oForm.StartPosition = FormStartPosition.CenterScreen
    oForm.TopMost = True
    oForm.FormBorderStyle = FormBorderStyle.FixedDialog
    oForm.MinimizeBox = False
    oForm.MaximizeBox = False
    oForm.Width = iFormW
    oForm.Height = 710

    ' ---- Header label ----
    Dim oLblHdr As New Label()
    oLblHdr.Text = "Set NEW model names below — applied FIRST. String rules will NOT rename any model listed here."
    oLblHdr.Left = 10 : oLblHdr.Top = 8 : oLblHdr.Width = iFormW - 20 : oLblHdr.Height = 18
    oForm.Controls.Add(oLblHdr)

    ' ---- Column headers — aligned above the field columns inside the scroll panel ----
    ' Offset = iPanelLeft + border(1) + field-left
    Dim iHdrOldLeft As Integer = iPanelLeft + 1 + iOldLeft
    Dim iHdrNewLeft As Integer = iPanelLeft + 1 + iNewLeft
    Dim oLblColOld As New Label()
    oLblColOld.Text = "CURRENT model name (read-only)"
    oLblColOld.Left = iHdrOldLeft : oLblColOld.Top = 30 : oLblColOld.Width = iOldW
    oForm.Controls.Add(oLblColOld)

    Dim oLblColNew As New Label()
    oLblColNew.Text = "NEW model name (editable)"
    oLblColNew.Left = iHdrNewLeft : oLblColNew.Top = 30 : oLblColNew.Width = iNewW
    oForm.Controls.Add(oLblColNew)

    ' ---- Scrollable panel ----
    Dim oPanel As New System.Windows.Forms.Panel()
    oPanel.Left = iPanelLeft : oPanel.Top = 50
    oPanel.Width = iPanelW : oPanel.Height = 490
    oPanel.AutoScroll = True
    oPanel.BorderStyle = BorderStyle.FixedSingle
    oForm.Controls.Add(oPanel)

    Dim iY As Integer = 6   ' current Y inside panel
    Dim iDrawingNum As Integer = 0

    For Each oEntry As Object() In oPhase0Data
        iDrawingNum += 1
        Dim sDwgBasename As String = CStr(oEntry(0))
        Dim oModelList As System.Collections.Generic.List(Of String) = _
            CType(oEntry(1), System.Collections.Generic.List(Of String))

        ' ── Drawing header row ──────────────────────────────────────────
        ' Left: sequence number + include checkbox
        Dim oLblNum As New Label()
        oLblNum.Text = iDrawingNum.ToString() & "."
        oLblNum.Left = 4 : oLblNum.Top = iY : oLblNum.Width = 22 : oLblNum.Height = 20
        oPanel.Controls.Add(oLblNum)

        Dim oChkInclude As New CheckBox()
        oChkInclude.Left = 26 : oChkInclude.Top = iY - 1 : oChkInclude.Width = 18 : oChkInclude.Height = 20
        oChkInclude.Checked = True   ' default ON — include this drawing
        oChkInclude.Tag = sDwgBasename
        oPanel.Controls.Add(oChkInclude)
        oIncludeCheckMap(sDwgBasename) = oChkInclude

        ' Drawing filename label (after checkbox) — append TB1_EN5_TYPE description if present
        Dim sDwgDesc As String = ""
        If oEntry.Length > 2 Then
            Try : sDwgDesc = CStr(oEntry(2)) : Catch : End Try
        End If
        Dim oLblDwg As New Label()
        oLblDwg.Text = If(sDwgDesc <> "", sDwgBasename & "  —  " & sDwgDesc, sDwgBasename)
        oLblDwg.Left = 46 : oLblDwg.Top = iY : oLblDwg.Width = 390 : oLblDwg.Height = 20
        oPanel.Controls.Add(oLblDwg)

        ' Right: "Match model states?" checkbox
        Dim oChkState As New CheckBox()
        oChkState.Text = "Match model states?"
        oChkState.Left = 440 : oChkState.Top = iY - 1 : oChkState.Width = 180 : oChkState.Height = 20
        oChkState.Checked = True
        oChkState.Tag = sDwgBasename
        oPanel.Controls.Add(oChkState)
        oStateCheckMap(sDwgBasename) = oChkState

        iY = iY + 24

        ' ── Bordered panel around old→new model rows ────────────────────
        Dim iModelPanelH As Integer = oModelList.Count * 26 + 6
        Dim oModelBorder As New System.Windows.Forms.Panel()
        oModelBorder.Left = iOldLeft : oModelBorder.Top = iY
        oModelBorder.Width = iPanelW - iOldLeft * 2 - 4
        oModelBorder.Height = iModelPanelH
        oModelBorder.BorderStyle = BorderStyle.FixedSingle
        oPanel.Controls.Add(oModelBorder)

        Dim iMY As Integer = 3   ' Y inside the bordered model panel

        ' One row per model in this drawing
        For Each sModelBasename As String In oModelList
            ' Left: old name label (read-only)
            Dim oLblOld As New Label()
            oLblOld.Text = sModelBasename
            oLblOld.Left = 2 : oLblOld.Top = iMY : oLblOld.Width = iOldW - 2 : oLblOld.Height = 20
            oModelBorder.Controls.Add(oLblOld)

            ' Arrow
            Dim oLblArr As New Label()
            oLblArr.Text = "->"
            oLblArr.Left = iOldW + 4 : oLblArr.Top = iMY : oLblArr.Width = 20 : oLblArr.Height = 20
            oModelBorder.Controls.Add(oLblArr)

            ' Right: editable or locked
            Dim iTxtLeft As Integer = iOldW + 26
            Dim iTxtW As Integer = oModelBorder.Width - iTxtLeft - 4
            If oMasterTxtMap.ContainsKey(sModelBasename) Then
                ' Already seen — show read-only mirror, synced to master
                Dim oTxtLocked As New System.Windows.Forms.TextBox()
                oTxtLocked.Left = iTxtLeft : oTxtLocked.Top = iMY : oTxtLocked.Width = iTxtW
                oTxtLocked.ReadOnly = True
                oTxtLocked.Text = oMasterTxtMap(sModelBasename).Text
                Dim oMasterRef As System.Windows.Forms.TextBox = oMasterTxtMap(sModelBasename)
                Dim oLockedRef As System.Windows.Forms.TextBox = oTxtLocked
                AddHandler oMasterRef.TextChanged, Sub(s, e) oLockedRef.Text = oMasterRef.Text
                oModelBorder.Controls.Add(oTxtLocked)
            Else
                ' First appearance — editable, pre-filled with the best available new name.
                ' Priority: 1) preset map (oExplicitModelRenameMap pre-loaded by caller)
                '           2) standard prefix-swap using oChoice.sReplace
                '           3) old name unchanged (fallback)
                Dim sPreFilled As String = sModelBasename
                If oChoice.oExplicitModelRenameMap.ContainsKey(sModelBasename) Then
                    ' Preset name from caller — use it directly
                    sPreFilled = oChoice.oExplicitModelRenameMap(sModelBasename)
                ElseIf Trim(oChoice.sReplace) <> "" Then
                    ' Standard prefix-swap: strip everything up to the first '-' and
                    ' replace with oChoice.sReplace (e.g. PJ00205).
                    Dim iMDash As Integer = sModelBasename.IndexOf("-"c)
                    If iMDash > 0 Then
                        Dim sOldPfx As String = sModelBasename.Substring(0, iMDash)
                        If String.Compare(sOldPfx, oChoice.sReplace, True) <> 0 Then
                            sPreFilled = oChoice.sReplace & sModelBasename.Substring(iMDash)
                        End If
                    End If
                End If
                Dim oTxtNew As New System.Windows.Forms.TextBox()
                oTxtNew.Left = iTxtLeft : oTxtNew.Top = iMY : oTxtNew.Width = iTxtW
                oTxtNew.Text = sPreFilled
                oTxtNew.Tag = sModelBasename
                ' All new-name fields are always editable — no locking, no grey.
                ' User can rename any model regardless of whether the auto-detected
                ' name is identical to the old name (e.g. to rename GA-direct subs).
                oModelBorder.Controls.Add(oTxtNew)
                oMasterTxtMap(sModelBasename) = oTxtNew
            End If

            iMY = iMY + 26
        Next

        iY = iY + iModelPanelH + 8   ' advance past bordered panel + gap
    Next

    ' ---- Footer controls ----
    ' ---- Report Only - Drawing/Model Grab checkbox ----
    ' Default OFF. When ticked and OK is clicked: write a text report of every
    ' drawing and its models (old name -> current NEW name field) to the Desktop,
    ' show a message and return False so no clean-sweep changes are made.
    Dim oChkReportOnly As New CheckBox()
    oChkReportOnly.Text = "Report Only – Drawing/Model Grab  (print list & exit, no changes)"
    oChkReportOnly.Left = 10
    oChkReportOnly.Top = 548
    oChkReportOnly.Width = 580
    oChkReportOnly.Checked = False
    oForm.Controls.Add(oChkReportOnly)

    ' Global include all / exclude all
    Dim oChkGlobalInclude As New CheckBox()
    oChkGlobalInclude.Text = "Include ALL drawings  (un-tick to exclude individual drawings above)"
    oChkGlobalInclude.Left = 10 : oChkGlobalInclude.Top = 572 : oChkGlobalInclude.Width = 450
    oChkGlobalInclude.Checked = True
    oForm.Controls.Add(oChkGlobalInclude)
    AddHandler oChkGlobalInclude.CheckedChanged, Sub(s, e)
        For Each oChk As CheckBox In oIncludeCheckMap.Values
            oChk.Checked = oChkGlobalInclude.Checked
        Next
    End Sub

    ' ---- Apply new model names checkbox ----
    ' Default OFF  → clean sweep: copy to new location, all names kept as pre-filled.
    ' Tick ON      → rename pass: apply whatever is typed in the NEW name fields.
    ' This is the master mode switch for the form.
    Dim oChkApplyNames As New CheckBox()
    oChkApplyNames.Text = "Apply new model names  (leave un-ticked for clean sweep - copies without renaming)"
    oChkApplyNames.Left = 10 : oChkApplyNames.Top = 596 : oChkApplyNames.Width = 580
    oChkApplyNames.Checked = False   ' default = clean sweep
    oForm.Controls.Add(oChkApplyNames)

    ' Initialise all new-name fields as read-only (clean sweep default).
    ' NOTE: System.Drawing.Color AND System.Drawing.SystemColors are both unavailable
    '       in the iLogic sandbox (System.Drawing.Primitives v8 not referenced).
    '       Do NOT set BackColor here — use ReadOnly only for edit-lock state.
    For Each oTxtInit As Object In oMasterTxtMap.Values
        CType(oTxtInit, System.Windows.Forms.TextBox).ReadOnly = True
    Next

    ' Toggle editable / read-only on all new-name fields when checkbox changes
    AddHandler oChkApplyNames.CheckedChanged, Sub(s, e)
        For Each oTxtToggle As Object In oMasterTxtMap.Values
            CType(oTxtToggle, System.Windows.Forms.TextBox).ReadOnly = Not oChkApplyNames.Checked
        Next
    End Sub

    ' ---- OK / Cancel — with bottom margin ----
    Dim oOk As New Button()
    oOk.Text = "OK" : oOk.DialogResult = DialogResult.OK
    oOk.Left = 476 : oOk.Top = 632 : oOk.Width = 80
    oForm.Controls.Add(oOk) : oForm.AcceptButton = oOk

    Dim oCancel As New Button()
    oCancel.Text = "Cancel" : oCancel.DialogResult = DialogResult.Cancel
    oCancel.Left = 568 : oCancel.Top = 632 : oCancel.Width = 80
    oForm.Controls.Add(oCancel) : oForm.CancelButton = oCancel

    If oForm.ShowDialog() <> DialogResult.OK Then Return False

    ' ---- Report Only - Drawing/Model Grab: write report to Desktop and exit ----
    If oChkReportOnly.Checked Then
        Dim sRptStamp As String = DateTime.Now.ToString("yyyy-MM-dd_HHmmss")
        Dim sRptFolder As String = System.Environment.GetFolderPath(System.Environment.SpecialFolder.Desktop)
        Dim sRptPath As String = System.IO.Path.Combine(sRptFolder, "DrawingModelGrab_" & sRptStamp & ".txt")
        Dim oRptSb As New System.Text.StringBuilder()
        Dim oRptEntry As Object()
        Dim sRptDwg As String
        Dim sRptDesc As String
        Dim oRptModels As System.Collections.Generic.List(Of String)
        Dim sRptMdl As String
        Dim sRptNew As String
        Dim iRptDwgCount As Integer = 0
        Dim iRptMdlCount As Integer = 0
        oRptSb.AppendLine("REPORT ONLY - Drawing/Model Grab")
        oRptSb.AppendLine("Generated : " & DateTime.Now.ToString())
        oRptSb.AppendLine("Status    : No files were copied, renamed, repointed or saved.")
        oRptSb.AppendLine(New String("="c, 100))
        For Each oRptEntry In oPhase0Data
            sRptDwg = CStr(oRptEntry(0))
            sRptDesc = ""
            If oRptEntry.Length > 2 Then
                Try
                    sRptDesc = CStr(oRptEntry(2))
                Catch
                    sRptDesc = ""
                End Try
            End If
            If sRptDesc <> "" Then
                oRptSb.AppendLine("DRAWING: " & sRptDwg & "  -  " & sRptDesc)
            Else
                oRptSb.AppendLine("DRAWING: " & sRptDwg)
            End If
            iRptDwgCount = iRptDwgCount + 1
            oRptModels = TryCast(oRptEntry(1), System.Collections.Generic.List(Of String))
            If oRptModels Is Nothing OrElse oRptModels.Count = 0 Then
                oRptSb.AppendLine("    (no model refs)")
            Else
                For Each sRptMdl In oRptModels
                    sRptNew = ""
                    If oMasterTxtMap.ContainsKey(sRptMdl) Then
                        sRptNew = Trim(oMasterTxtMap(sRptMdl).Text)
                    End If
                    oRptSb.AppendLine("    " & sRptMdl & " -> " & sRptNew)
                    iRptMdlCount = iRptMdlCount + 1
                Next
            End If
            oRptSb.AppendLine("")
        Next
        oRptSb.AppendLine(New String("="c, 100))
        oRptSb.AppendLine("Drawings : " & iRptDwgCount)
        oRptSb.AppendLine("Model rows: " & iRptMdlCount)
        Try
            System.IO.File.WriteAllText(sRptPath, oRptSb.ToString())
            MessageBox.Show("Report Only - Drawing/Model Grab written to:" & vbCrLf & sRptPath & vbCrLf & vbCrLf & "No changes were made.", "Drawing/Model Grab")
        Catch exRpt As Exception
            MessageBox.Show("Could not write report: " & exRpt.Message, "Drawing/Model Grab")
        End Try
        Return False
    End If

    ' ---- Collect results ----
    oChoice.oExplicitModelRenameMap.Clear()
    Dim bApplyNames As Boolean = oChkApplyNames.Checked
    For Each kvp As System.Collections.Generic.KeyValuePair(Of String, System.Windows.Forms.TextBox) In oMasterTxtMap
        Dim sOldBase As String = kvp.Key
        ' If "Apply new model names" is unchecked (clean sweep), use the old name regardless
        ' of what's in the text field — no renaming, just copy to new location.
        Dim sNewBase As String = If(bApplyNames, Trim(kvp.Value.Text), sOldBase)
        If sNewBase = "" Then sNewBase = sOldBase   ' blank → keep original
        ' Strip any extension the user may have typed (e.g. ".iam") — the copy step
        ' always preserves the original file's extension, so storing a bare stem here
        ' prevents double-extension filenames like PJ00205-3450-001-V01-00.iam.iam.
        sNewBase = System.IO.Path.GetFileNameWithoutExtension(sNewBase)
        If sNewBase = "" Then sNewBase = System.IO.Path.GetFileNameWithoutExtension(sOldBase)
        oChoice.oExplicitModelRenameMap(sOldBase) = sNewBase
    Next

    ' oDrawingStateMatch = include flag (True = pre-tick this drawing in the selection form)
    oChoice.oDrawingStateMatch.Clear()
    For Each kvp As System.Collections.Generic.KeyValuePair(Of String, CheckBox) In oIncludeCheckMap
        oChoice.oDrawingStateMatch(kvp.Key) = kvp.Value.Checked
    Next

    Return True
End Function


Function GetSetExitFlag(Optional bSet As Boolean = False, Optional bNewVal As Boolean = False) As Boolean
    Static bExitRequested As Boolean = False
    If bSet Then bExitRequested = bNewVal
    Return bExitRequested
End Function

' Counts how many Continue/Exit dialogs have been shown this run so we
' never spam the user on a cascade of failures.
Function GetSetExitDialogCount(Optional bSet As Boolean = False, Optional iNewVal As Integer = 0) As Integer
    Static iCount As Integer = 0
    If bSet Then iCount = iNewVal
    Return iCount
End Function

Sub ResetExitFlag()
    GetSetExitFlag(True, False)
    GetSetExitDialogCount(True, 0)
End Sub

Function IsExitRequested() As Boolean
    Return GetSetExitFlag()
End Function


Function GetSetExcelApp(Optional bSet As Boolean = False, Optional oNewVal As Object = Nothing) As Object
    Static oXLStatic As Object = Nothing
    If bSet Then oXLStatic = oNewVal
    Return oXLStatic
End Function


' ---------------------------------------------------------------------
' MEMORY MANAGEMENT (prevents Inventor ballooning to multi-GB mid-run)
' ---------------------------------------------------------------------
' Snapshot of documents already open when the rule started. Anything we
' Documents.Open() during the run that is NOT in this set is a candidate
' to close as soon as we are finished with it, and again in the final
' cleanup pass. Without this, every Open stays resident until the rule
' ends - on a large tree that is hundreds of documents and multi-GB.
Function GetSetInitiallyOpenDocs(Optional bSet As Boolean = False, _
    Optional oNewVal As System.Collections.Generic.HashSet(Of String) = Nothing) As System.Collections.Generic.HashSet(Of String)
    Static oInitOpen As System.Collections.Generic.HashSet(Of String) = Nothing
    If bSet Then oInitOpen = oNewVal
    If oInitOpen Is Nothing Then oInitOpen = New System.Collections.Generic.HashSet(Of String)(StringComparer.OrdinalIgnoreCase)
    Return oInitOpen
End Function

Function GetSetGcCounter(Optional bSet As Boolean = False, Optional iNewVal As Integer = 0) As Integer
    Static iGc As Integer = 0
    If bSet Then iGc = iNewVal
    Return iGc
End Function

' Capture FullFileNames of every document currently in the session.
Sub SnapshotInitiallyOpenDocuments()
    Dim oSet As New System.Collections.Generic.HashSet(Of String)(StringComparer.OrdinalIgnoreCase)
    Try
        For Each oD As Document In ThisApplication.Documents
            Try
                Dim sP As String = oD.FullFileName
                If Trim(sP) <> "" Then oSet.Add(sP)
            Catch
            End Try
        Next
    Catch
    End Try
    GetSetInitiallyOpenDocs(True, oSet)
    GetSetGcCounter(True, 0)
End Sub

' True if this path was already open when the rule started.
Function WasInitiallyOpen(sFullPath As String) As Boolean
    If Trim(sFullPath) = "" Then Return True
    Return GetSetInitiallyOpenDocs().Contains(sFullPath)
End Function

' Open a document only if needed. Sets bOpenedHere=True when WE opened it
' (caller should CloseIfOpenedHere when finished). Never throws - returns Nothing on failure.
Function OpenDocTracked(sFullPath As String, ByRef bOpenedHere As Boolean) As Document
    bOpenedHere = False
    If Trim(sFullPath) = "" OrElse sFullPath.Contains("*") Then Return Nothing
    Dim oDoc As Document = Nothing
    Try
        Try : oDoc = ThisApplication.Documents.ItemByName(sFullPath) : Catch : oDoc = Nothing : End Try
        If oDoc IsNot Nothing Then Return oDoc
        If Not System.IO.File.Exists(sFullPath) Then Return Nothing
        oDoc = ThisApplication.Documents.Open(sFullPath, False)
        bOpenedHere = True
        ' Periodic GC every 20 opens we perform - stops slow COM accumulation
        Dim iC As Integer = GetSetGcCounter() + 1
        GetSetGcCounter(True, iC)
        If (iC Mod 20) = 0 Then
            Try : GC.Collect() : GC.WaitForPendingFinalizers() : Catch : End Try
        End If
        Return oDoc
    Catch
        Return Nothing
    End Try
End Function

' Close a document we opened, provided it was not already open at rule start
' and is not dirty (unsaved work we still need). Safe to call with Nothing.
Sub CloseIfOpenedHere(oDoc As Document, bOpenedHere As Boolean)
    If Not bOpenedHere Then Return
    If oDoc Is Nothing Then Return
    Try
        Dim sP As String = ""
        Try : sP = oDoc.FullFileName : Catch : End Try
        ' Never close something that was already in the session at start
        If sP <> "" AndAlso WasInitiallyOpen(sP) Then Return
        Dim bDirty As Boolean = False
        Try : bDirty = oDoc.Dirty : Catch : End Try
        If bDirty Then Return
        oDoc.Close(False)
    Catch
    End Try
End Sub

' Force a GC tick from long loops that do not Open (e.g. pure occurrence walks).
Sub PeriodicGcTick()
    Dim iC As Integer = GetSetGcCounter() + 1
    GetSetGcCounter(True, iC)
    If (iC Mod 25) = 0 Then
        Try : GC.Collect() : GC.WaitForPendingFinalizers() : Catch : End Try
    End If
End Sub


' Copy spreadsheet / text parameter sources WITHOUT starting Excel whenever
' possible. Workbooks.Open was the main source of recovery / "file in use"
' pop-ups even with DisplayAlerts=False. Order:
'   1) Already on disk at dest -> success
'   2) System.IO.File.Copy (preferred - no Excel)
'   3) Excel Open/SaveAs only as last resort (locked or damaged source)
Function CopyXlsxSilently(sSourceFull As String, sDestFull As String) As Boolean
    If Trim(sSourceFull) = "" OrElse Trim(sDestFull) = "" Then Return False
    If String.Compare(sSourceFull, sDestFull, True) = 0 Then Return System.IO.File.Exists(sDestFull)

    ' Already present (previous pass / earlier run) - still clear RO in case
    ' the file was copied from a Vault-checked-in source and inherited RO.
    If System.IO.File.Exists(sDestFull) Then
        Try
            Dim oEx As System.IO.FileAttributes = System.IO.File.GetAttributes(sDestFull)
            If (oEx And System.IO.FileAttributes.ReadOnly) = System.IO.FileAttributes.ReadOnly Then
                System.IO.File.SetAttributes(sDestFull, oEx And Not System.IO.FileAttributes.ReadOnly)
            End If
        Catch
        End Try
        Return True
    End If

    Try
        Dim sDestDir As String = System.IO.Path.GetDirectoryName(sDestFull)
        If sDestDir <> "" AndAlso Not System.IO.Directory.Exists(sDestDir) Then
            System.IO.Directory.CreateDirectory(sDestDir)
        End If
    Catch
    End Try

    ' 1) Prefer pure OS copy - never launches Excel
    Try
        If System.IO.File.Exists(sSourceFull) Then
            System.IO.File.Copy(sSourceFull, sDestFull, True)
            If System.IO.File.Exists(sDestFull) Then
                Try
                    Dim oA As System.IO.FileAttributes = System.IO.File.GetAttributes(sDestFull)
                    If (oA And System.IO.FileAttributes.ReadOnly) = System.IO.FileAttributes.ReadOnly Then
                        System.IO.File.SetAttributes(sDestFull, oA And Not System.IO.FileAttributes.ReadOnly)
                    End If
                Catch
                End Try
                Return True
            End If
        End If
    Catch
    End Try

    ' 2) Last resort: Excel COM (only if File.Copy failed and we have an app)
    Dim oXL As Object = GetSetExcelApp()
    If oXL Is Nothing Then Return False
    Try
        oXL.DisplayAlerts = False
        Try : oXL.ScreenUpdating = False : Catch : End Try
        Try : oXL.EnableEvents = False : Catch : End Try
        Try : oXL.AskToUpdateLinks = False : Catch : End Try
        ' UpdateLinks:=0, ReadOnly:=True - minimise prompts
        Dim oWB As Object = oXL.Workbooks.Open(sSourceFull, 0, True)
        Try
            oWB.SaveAs(sDestFull)
        Finally
            Try : oWB.Close(False) : Catch : End Try
        End Try
        If System.IO.File.Exists(sDestFull) Then
            Try
                Dim oA2 As System.IO.FileAttributes = System.IO.File.GetAttributes(sDestFull)
                If (oA2 And System.IO.FileAttributes.ReadOnly) = System.IO.FileAttributes.ReadOnly Then
                    System.IO.File.SetAttributes(sDestFull, oA2 And Not System.IO.FileAttributes.ReadOnly)
                End If
            Catch
            End Try
            Return True
        End If
    Catch
    End Try
    Return False
End Function

' Shown only for hard file-operation failures (copy/SaveAs of a design file).
' Max 5 dialogs per run so a cascade of failures does not spam the user.
' Cancel sets the exit flag; subsequent work checks IsExitRequested().
Sub CheckContinueOrExit(sFailureDescription As String, sLogFilePath As String)
    If IsExitRequested() Then Return
    Dim iShown As Integer = GetSetExitDialogCount()
    If iShown >= 5 Then
        ' Too many failures already - auto-exit so the user can fix and re-run
        GetSetExitFlag(True, True)
        Try
            System.IO.File.AppendAllText(sLogFilePath, vbCrLf & _
                "AUTO EARLY EXIT after 5 failures. Last: " & sFailureDescription & vbCrLf)
        Catch
        End Try
        Return
    End If
    Try
        Dim sMsg As String = "A file operation could not be completed:" & vbCrLf & vbCrLf & _
            sFailureDescription & vbCrLf & vbCrLf & _
            "[OK]     Continue - log this and keep processing." & vbCrLf & _
            "[Cancel] Exit Rule - stop now so you can fix and re-run." & vbCrLf & vbCrLf & _
            "(Dialog " & (iShown + 1).ToString() & " of 5 max this run)"
        Dim oResult As System.Windows.Forms.DialogResult = MessageBox.Show( _
            sMsg, "Continue or Exit?", _
            System.Windows.Forms.MessageBoxButtons.OKCancel, _
            System.Windows.Forms.MessageBoxIcon.Warning)
        GetSetExitDialogCount(True, iShown + 1)
        If oResult = System.Windows.Forms.DialogResult.Cancel Then
            GetSetExitFlag(True, True)
            Try : System.IO.File.AppendAllText(sLogFilePath, vbCrLf & "USER REQUESTED EARLY EXIT." & vbCrLf) : Catch : End Try
        End If
    Catch
    End Try
End Sub




' Writes a snapshot of every occurrence's ORIGINAL file in the tree to
' sSnapshotPath, so the assembly can be reverted later. Each occurrence
' is identified by a breadcrumb of occurrence NAMES from the top down
' (not just a file name, since the same file name can appear in more
' than one branch) - occurrence names stay stable even after Replace()
' repoints them to a different file, so this breadcrumb will still
' resolve correctly in a companion "revert" rule even after this rule
' =====================================================================
' PASS MANIFEST WRITER
' =====================================================================
' Writes a structured old-path -> new-path table to sTargetFolder.
' File name: <GA basename>_RenameMap_Pass1.txt, _Pass2.txt, ... auto-numbered.
' Format is tab-separated with a header, suitable for diff or scripted revert.
' Returns the full path of the file written.
' =====================================================================
Function WritePassManifest( _
    sTargetFolder As String, _
    sGABasename As String, _
    oRenameMap As System.Collections.Generic.Dictionary(Of String, String), _
    oLog As System.Text.StringBuilder) As String

    ' Auto-number: single folder listing to find highest existing pass N, then use N+1 (Fix #8)
    Dim iPass As Integer = 1
    Try
        Dim oExisting() As String = System.IO.Directory.GetFiles(sTargetFolder, sGABasename & "_RenameMap_Pass*.txt")
        Dim iMax As Integer = 0
        For Each sF As String In oExisting
            Dim sBase As String = System.IO.Path.GetFileNameWithoutExtension(sF)
            Dim iPassStart As Integer = sBase.LastIndexOf("_Pass")
            If iPassStart >= 0 Then
                Dim iNum As Integer = 0
                If Integer.TryParse(sBase.Substring(iPassStart + 5), iNum) Then
                    If iNum > iMax Then iMax = iNum
                End If
            End If
        Next
        iPass = iMax + 1
    Catch
        ' Fallback: probe individually
        Do While System.IO.File.Exists( _
            System.IO.Path.Combine(sTargetFolder, sGABasename & "_RenameMap_Pass" & iPass & ".txt"))
            iPass = iPass + 1
        Loop
    End Try

    Dim sPath As String = System.IO.Path.Combine(sTargetFolder, sGABasename & "_RenameMap_Pass" & iPass & ".txt")

    Dim oLines As New System.Collections.Generic.List(Of String)
    oLines.Add("TRAVERSE Pass Manifest — Pass " & iPass)
    oLines.Add("Generated : " & DateTime.Now.ToString("yyyy-MM-dd HH:mm:ss"))
    oLines.Add("Assembly  : " & sGABasename)
    oLines.Add("Entries   : " & If(oRenameMap IsNot Nothing, oRenameMap.Count, 0).ToString)
    oLines.Add("")
    oLines.Add("OLD PATH" & vbTab & "NEW PATH")
    oLines.Add(New String("-"c, 80))

    If oRenameMap IsNot Nothing Then
        ' Sort by old path for consistent, diffable output
        Dim oKeys As New System.Collections.Generic.List(Of String)(oRenameMap.Keys)
        oKeys.Sort(StringComparer.OrdinalIgnoreCase)
        For Each sOld As String In oKeys
            Dim sNew As String = ""
            oRenameMap.TryGetValue(sOld, sNew)
            ' Flag no-change entries (relocate only or locked tier-1)
            Dim sTag As String = ""
            If String.Compare(System.IO.Path.GetFileName(sOld), System.IO.Path.GetFileName(sNew), True) = 0 Then
                sTag = vbTab & "[RELOCATE-ONLY]"
            End If
            oLines.Add(sOld & vbTab & sNew & sTag)
        Next
    End If

    oLines.Add("")
    oLines.Add("--- END OF PASS " & iPass & " MANIFEST ---")
    oLines.Add("To reverse this pass: swap OLD PATH and NEW PATH columns and re-run a restore script.")

    System.IO.File.WriteAllLines(sPath, oLines)
    oLog.Append(vbCrLf & "Pass manifest written: " & System.IO.Path.GetFileName(sPath))
    Return sPath

End Function


' =====================================================================
' ORIGINAL STATE SNAPSHOT
' =====================================================================
' has renamed things. Uses the same current-path cycle guard and
' virtual-component handling as the main rename traversal, but is
' entirely read-only - it never renames, saves, or repoints anything.
Sub CaptureOriginalState(oAsmDoc As AssemblyDocument, sSnapshotPath As String)

    Dim sLines As New System.Collections.Generic.List(Of String)
    sLines.Add("Snapshot captured: " & DateTime.Now.ToString())
    sLines.Add("Top assembly: " & oAsmDoc.FullFileName)
    sLines.Add("Format: <breadcrumb of occurrence names from the top down>  =>  <original full file path>")
    sLines.Add("")

    Dim oPathStack As New System.Collections.Generic.List(Of String)
    Dim oVisited As New System.Collections.Generic.HashSet(Of String)

    CaptureLevel(oAsmDoc.ComponentDefinition, oPathStack, oVisited, sLines)

    System.IO.File.WriteAllLines(sSnapshotPath, sLines)

End Sub


' Recursively walks one level for CaptureOriginalState above. Records
' EVERY occurrence (not deduplicated by file, unlike the rename
' traversal) since a revert needs to repoint each one individually,
' including duplicate/pattern instances of the same file.
Sub CaptureLevel(oCompDef As ComponentDefinition, ByRef oPathStack As System.Collections.Generic.List(Of String), ByRef oVisited As System.Collections.Generic.HashSet(Of String), ByRef sLines As System.Collections.Generic.List(Of String))

    Dim sThisLevelFullName As String = oCompDef.Document.FullFileName

    ' Current-path cycle guard - same reasoning as the rename traversal:
    ' a shared component reached from a different branch is normal and
    ' should still be captured; only a genuine ancestor-of-itself cycle
    ' is refused.
    If oVisited.Contains(sThisLevelFullName) Then Exit Sub
    oVisited.Add(sThisLevelFullName)

    Try
        For Each oOcc As ComponentOccurrence In oCompDef.Occurrences

            ' Include suppressed occurrences in the snapshot - they have real
            ' file references and must be captured for a complete picture.
            Dim sSuppTag As String = If(oOcc.Suppressed, " [SUPPRESSED]", "")

            Dim oRefDoc As Document = Nothing
            Try
                oRefDoc = oOcc.Definition.Document
            Catch
                Continue For ' virtual component with no document at all - nothing to capture
            End Try

            Dim sOccFullName As String = oRefDoc.FullFileName
            If sOccFullName = "" Then Continue For ' virtual component - no separate file to capture
            If IsSyntheticPatternMemberName(sOccFullName) Then Continue For ' pattern-member synthetic name, not a real file - nothing to capture

            oPathStack.Add(oOcc.Name)
            sLines.Add(String.Join(" > ", oPathStack) & "  =>  " & sOccFullName & sSuppTag)

            ' Virtual assemblies share identity with their host and must
            ' never be recursed into (same infinite-loop lesson as the
            ' rename rule) - only recurse into a REAL, separately-filed
            ' sub-assembly.
            If oRefDoc.DocumentType = kAssemblyDocumentObject AndAlso String.Compare(sOccFullName, sThisLevelFullName, True) <> 0 Then
                CaptureLevel(oRefDoc.ComponentDefinition, oPathStack, oVisited, sLines)
            End If

            oPathStack.RemoveAt(oPathStack.Count - 1)

        Next
    Finally
        oVisited.Remove(sThisLevelFullName)
    End Try

End Sub


' Holds the result of the mode/find/replace picker below.
Class RenameModeChoice
    Public bCancelled As Boolean = False
    Public bUseContainsMode As Boolean = False ' False = Mode 1 (prefix swap), True = Mode 2 (segment replace)
    Public bConsolidateOnlyMode As Boolean = False ' Mode 3 - relocate only, no renaming
    Public bBatchMode As Boolean = False         ' Mode 4 - batch P-prefix scan and swap
    Public bVerifyOnlyMode As Boolean = False    ' Mode 5 - verify only (read-only scan)
    Public bCopyDesignMode As Boolean = False    ' Mode 6 - Vault Copy Design style (one-pass)
    Public sFind As String = ""                  ' single Find token (Modes 1/2/3)
    Public sReplace As String = ""               ' new project number (all modes)
    ' Mode 4 / Mode 6: list of Find tokens selected by the user
    Public oBatchFinds As New System.Collections.Generic.List(Of String)
    ' Mode 6: up to 5 optional segment find/replace pairs (applied after prefix swap)
    Public oSegFinds As New System.Collections.Generic.List(Of String)
    Public oSegReplaces As New System.Collections.Generic.List(Of String)
    ' Mode 6: localize non-PJ / non-std parts into Non Std Parts with new prefix
    Public bLocalizeNonStd As Boolean = True
    ' Mode 6: user-selected destination folder for the new assembly copies
    ' Empty string = use the source assembly's own folder (in-place rename)
    Public sTargetFolder As String = ""
    ' Mode 6: folder structure mode
    '   False = CLEAN SINGLE FOLDER  - all renamed files land flat in sTargetFolder (current behaviour)
    '   True  = HONOUR EXISTING      - files keep their relative sub-folder path inside sTargetFolder
    Public bHonourFolderStructure As Boolean = False
    ' Mode 6 Drawing Update: run RunDrawingUpdatePass after TRAVERSE completes
    Public bUpdateDrawings As Boolean = False
    ' Mode 6 Drawing Update: flat drawings folder path (all .idw files to update)
    Public sDrawingsFolder As String = ""
    ' Mode 6 Drawing Model Rename: skip explicit rename form - keep all drawing model names as-is
    Public bKeepDrawingModelNames As Boolean = False
    ' Mode 6 Drawing Model Rename: explicit map - old model basename -> new model basename (user-confirmed)
    ' Populated from ShowDrawingModelRenameForm or self-mapped when bKeepDrawingModelNames=True
    Public oExplicitModelRenameMap As New System.Collections.Generic.Dictionary(Of String, String)(StringComparer.OrdinalIgnoreCase)
    ' Mode 6 Drawing Model Rename: per-drawing "match model states?" flag
    ' Key = drawing filename (basename), Value = True to re-assert model states after ReplaceReference
    Public oDrawingStateMatch As New System.Collections.Generic.Dictionary(Of String, Boolean)(StringComparer.OrdinalIgnoreCase)
    ' Mode 6 Re-run detection: True when an existing GA copy was found in the target folder.
    ' ShowCopyDesignConfigForm greys out the new-prefix field when this is True.
    Public bPrefixLocked As Boolean = False
End Class


' Single dialog covering both the mode choice and the find/replace text,
' so there's no ambiguity about which behaviour is about to run.
Function ShowRenameModeForm() As RenameModeChoice

    Dim oResult As New RenameModeChoice

    Dim oForm As New Form()
    oForm.Text = "Choose Rename Mode"
    oForm.StartPosition = FormStartPosition.CenterScreen
    oForm.TopMost = True
    oForm.FormBorderStyle = FormBorderStyle.FixedDialog
    oForm.MinimizeBox = False
    oForm.MaximizeBox = False
    oForm.Width = 580
    oForm.Height = 900

    ' ── Layout: each block = checkbox (top N) + indented label (top N+23) ──
    ' Heights are set generously so text never clips into the next block.
    '  Mode 1  chk=15   lbl=38  h=32  → next=80
    '  Mode 2  chk=80   lbl=103 h=52  → next=165
    '  Mode 3  chk=165  lbl=188 h=80  → next=278
    '  Mode 4  chk=278  lbl=301 h=52  → next=363
    '  Mode 5  chk=363  lbl=386 h=45  → next=441
    '  Mode 6  chk=441  lbl=464 h=48  → next=522
    '  Find        top=532
    '  Replace     top=568
    '  Note        top=608  h=70
    '  OK/Cancel   top=820

    Dim oChkPrefix As New CheckBox()
    oChkPrefix.Text = "Mode 1 - Swap PROJECT PREFIX (file name STARTS WITH Find)"
    oChkPrefix.Left = 15
    oChkPrefix.Top = 15
    oChkPrefix.Width = 500
    oChkPrefix.Checked = True
    oForm.Controls.Add(oChkPrefix)

    Dim oLblPrefixExample As New Label()
    oLblPrefixExample.Text = "e.g. Find 'PJ00195-3620', Replace 'PJ00195-3610' - only the matched" & vbCrLf & "leading text changes; everything after it is kept as-is."
    oLblPrefixExample.Left = 35
    oLblPrefixExample.Top = 38
    oLblPrefixExample.Width = 490
    oLblPrefixExample.Height = 32
    oForm.Controls.Add(oLblPrefixExample)

    Dim oChkSegment As New CheckBox()
    oChkSegment.Text = "Mode 2 - Replace a SEGMENT anywhere in the name (file name CONTAINS Find)"
    oChkSegment.Left = 15
    oChkSegment.Top = 80
    oChkSegment.Width = 500
    oChkSegment.Checked = False
    oForm.Controls.Add(oChkSegment)

    Dim oLblSegmentExample As New Label()
    oLblSegmentExample.Text = "e.g. Find '3620', Replace '3610' - just that piece of text is swapped" & vbCrLf & "wherever it appears; everything else in the name is untouched." & vbCrLf & "Leave Replace BLANK to strip the text out entirely (e.g. Find '_DEL'" & vbCrLf & "removes even a doubled-up '_DEL_DEL' suffix down to nothing)."
    oLblSegmentExample.Left = 35
    oLblSegmentExample.Top = 103
    oLblSegmentExample.Width = 490
    oLblSegmentExample.Height = 52
    oForm.Controls.Add(oLblSegmentExample)

    Dim oChkConsolidate As New CheckBox()
    oChkConsolidate.Text = "Mode 3 - CONSOLIDATE ONLY (relocate into this folder, no renaming)"
    oChkConsolidate.Left = 15
    oChkConsolidate.Top = 165
    oChkConsolidate.Width = 500
    oChkConsolidate.Checked = False
    oForm.Controls.Add(oChkConsolidate)

    Dim oLblConsolidateExample As New Label()
    oLblConsolidateExample.Text = "Only FIND is used (as a STARTS WITH match, same as Mode 1) - names" & vbCrLf & "are never changed. Any matching sub NOT already sitting in this" & vbCrLf & "assembly's folder gets an independent copy made here FIRST, then its" & vbCrLf & "own children are consolidated inside that copy - the original file is" & vbCrLf & "only ever read from, never modified. Safe to use even when the" & vbCrLf & "original files are still shared with other, untouched assemblies."
    oLblConsolidateExample.Left = 35
    oLblConsolidateExample.Top = 188
    oLblConsolidateExample.Width = 490
    oLblConsolidateExample.Height = 80
    oForm.Controls.Add(oLblConsolidateExample)

    Dim oChkBatch As New CheckBox()
    oChkBatch.Text = "Mode 4 - BATCH P-PREFIX SWAP (scan tree, pick which old project numbers to replace)"
    oChkBatch.Left = 15
    oChkBatch.Top = 278
    oChkBatch.Width = 510
    oChkBatch.Checked = False
    oForm.Controls.Add(oChkBatch)

    Dim oLblBatchExample As New Label()
    oLblBatchExample.Text = "Scans the full tree, finds every unique P-prefix (PJ00184, PJ174," & vbCrLf & _
        "PM00777 etc.) with file counts. You pick ALL or a subset, enter" & vbCrLf & _
        "one new project number, and every selected old prefix is swapped" & vbCrLf & _
        "in one run. Find and Replace fields below are not used in this mode."
    oLblBatchExample.Left = 35
    oLblBatchExample.Top = 301
    oLblBatchExample.Width = 490
    oLblBatchExample.Height = 52
    oForm.Controls.Add(oLblBatchExample)

    Dim oChkVerify As New CheckBox()
    oChkVerify.Text = "Mode 5 - VERIFY ONLY (read-only scan - reports remaining old-prefix references)"
    oChkVerify.Left = 15
    oChkVerify.Top = 363
    oChkVerify.Width = 510
    oChkVerify.Checked = False
    oForm.Controls.Add(oChkVerify)

    Dim oLblVerifyExample As New Label()
    oLblVerifyExample.Text = "No files copied, renamed, or saved. Scans the full tree and" & vbCrLf & _
        "writes a report of every remaining old-prefix reference to the" & vbCrLf & _
        "decisions log. Use before Mode 4 to preview, or after to verify."
    oLblVerifyExample.Left = 35
    oLblVerifyExample.Top = 386
    oLblVerifyExample.Width = 490
    oLblVerifyExample.Height = 45
    oForm.Controls.Add(oLblVerifyExample)

    Dim oChkCopyDesign As New CheckBox()
    oChkCopyDesign.Text = "Mode 6 - COPY DESIGN (Vault-style one-pass: prefix + segments + non-std)"
    oChkCopyDesign.Left = 15
    oChkCopyDesign.Top = 441
    oChkCopyDesign.Width = 530
    oChkCopyDesign.Checked = False
    oForm.Controls.Add(oChkCopyDesign)

    Dim oLblCopyDesignExample As New Label()
    oLblCopyDesignExample.Text = "One pass like Vault Copy Design: pick old prefixes, new project number," & vbCrLf & _
        "up to 4 optional segment replaces, and optionally localize non-std" & vbCrLf & _
        "parts into Non Std Parts. Modes 1-5 stay available for isolated tests."
    oLblCopyDesignExample.Left = 35
    oLblCopyDesignExample.Top = 464
    oLblCopyDesignExample.Width = 500
    oLblCopyDesignExample.Height = 48
    oForm.Controls.Add(oLblCopyDesignExample)

    Dim oLblFind As New Label()
    oLblFind.Text = "Find:"
    oLblFind.Left = 15
    oLblFind.Top = 532
    oLblFind.Width = 80
    oForm.Controls.Add(oLblFind)

    Dim oTxtFind As New System.Windows.Forms.TextBox()
    oTxtFind.Left = 100
    oTxtFind.Top = 529
    oTxtFind.Width = 420
    oForm.Controls.Add(oTxtFind)

    Dim oLblReplace As New Label()
    oLblReplace.Text = "Replace with:"
    oLblReplace.Left = 15
    oLblReplace.Top = 568
    oLblReplace.Width = 80
    oForm.Controls.Add(oLblReplace)

    Dim oTxtReplace As New System.Windows.Forms.TextBox()
    oTxtReplace.Left = 100
    oTxtReplace.Top = 565
    oTxtReplace.Width = 420
    oForm.Controls.Add(oTxtReplace)

    Dim oNote As New Label()
    oNote.Text = "Applies to parts, sub-assemblies, derived sources, and linked" & vbCrLf & _
        "parameter tables (all modes). Library / Content Center / SJD00-GT" & vbCrLf & _
        "Standard folders are always skipped. Modes 1-5 = surgical tests;" & vbCrLf & _
        "Mode 6 = production Copy Design (one map, one pass)."
    oNote.Left = 15
    oNote.Top = 608
    oNote.Width = 520
    oNote.Height = 70
    oForm.Controls.Add(oNote)

    ' Keep mode checkboxes mutually exclusive.
    Dim UpdateFields As Action = Sub()
        Dim bDisableAll As Boolean = oChkBatch.Checked OrElse oChkVerify.Checked OrElse oChkCopyDesign.Checked
        oTxtFind.Enabled    = Not bDisableAll
        oTxtReplace.Enabled = Not bDisableAll AndAlso Not oChkConsolidate.Checked
        oLblFind.Enabled    = Not bDisableAll
        oLblReplace.Enabled = Not bDisableAll AndAlso Not oChkConsolidate.Checked
    End Sub
    AddHandler oChkPrefix.CheckedChanged, Sub(sender, e)
        If oChkPrefix.Checked Then
            oChkSegment.Checked = False : oChkConsolidate.Checked = False
            oChkBatch.Checked = False : oChkVerify.Checked = False : oChkCopyDesign.Checked = False
        End If
        UpdateFields()
    End Sub
    AddHandler oChkSegment.CheckedChanged, Sub(sender, e)
        If oChkSegment.Checked Then
            oChkPrefix.Checked = False : oChkConsolidate.Checked = False
            oChkBatch.Checked = False : oChkVerify.Checked = False : oChkCopyDesign.Checked = False
        End If
        UpdateFields()
    End Sub
    AddHandler oChkConsolidate.CheckedChanged, Sub(sender, e)
        If oChkConsolidate.Checked Then
            oChkPrefix.Checked = False : oChkSegment.Checked = False
            oChkBatch.Checked = False : oChkVerify.Checked = False : oChkCopyDesign.Checked = False
        End If
        UpdateFields()
    End Sub
    AddHandler oChkBatch.CheckedChanged, Sub(sender, e)
        If oChkBatch.Checked Then
            oChkPrefix.Checked = False : oChkSegment.Checked = False
            oChkConsolidate.Checked = False : oChkVerify.Checked = False : oChkCopyDesign.Checked = False
        End If
        UpdateFields()
    End Sub
    AddHandler oChkVerify.CheckedChanged, Sub(sender, e)
        If oChkVerify.Checked Then
            oChkPrefix.Checked = False : oChkSegment.Checked = False
            oChkConsolidate.Checked = False : oChkBatch.Checked = False : oChkCopyDesign.Checked = False
        End If
        UpdateFields()
    End Sub
    AddHandler oChkCopyDesign.CheckedChanged, Sub(sender, e)
        If oChkCopyDesign.Checked Then
            oChkPrefix.Checked = False : oChkSegment.Checked = False
            oChkConsolidate.Checked = False : oChkBatch.Checked = False : oChkVerify.Checked = False
        End If
        UpdateFields()
    End Sub

    Dim oOkButton As New Button()
    oOkButton.Text = "OK"
    oOkButton.DialogResult = DialogResult.OK
    oOkButton.Left = 350
    oOkButton.Top = 820
    oOkButton.Width = 90
    oForm.Controls.Add(oOkButton)
    oForm.AcceptButton = oOkButton

    Dim oCancelButton As New Button()
    oCancelButton.Text = "Cancel"
    oCancelButton.DialogResult = DialogResult.Cancel
    oCancelButton.Left = 450
    oCancelButton.Top = 820
    oCancelButton.Width = 90
    oForm.Controls.Add(oCancelButton)
    oForm.CancelButton = oCancelButton

    Dim oDialogResult As DialogResult = oForm.ShowDialog()

    If oDialogResult <> DialogResult.OK Then
        oResult.bCancelled = True
        Return oResult
    End If

    ' Only FIND is required in Modes 1/2/3 - REPLACE may be blank (strip text).
    If Not oChkBatch.Checked AndAlso Not oChkVerify.Checked AndAlso Not oChkCopyDesign.Checked AndAlso Trim(oTxtFind.Text) = "" Then
        MessageBox.Show("Find must be filled in - rule cancelled.", "Cancelled")
        oResult.bCancelled = True
        Return oResult
    End If

    oResult.bUseContainsMode = oChkSegment.Checked
    oResult.bConsolidateOnlyMode = oChkConsolidate.Checked
    oResult.bBatchMode = oChkBatch.Checked
    oResult.bVerifyOnlyMode = oChkVerify.Checked
    oResult.bCopyDesignMode = oChkCopyDesign.Checked
    If Not oChkBatch.Checked AndAlso Not oChkVerify.Checked AndAlso Not oChkCopyDesign.Checked Then
        oResult.sFind = Trim(oTxtFind.Text)
        oResult.sReplace = Trim(oTxtReplace.Text)
    End If

    Return oResult

End Function


' Case-insensitive find/replace of EVERY occurrence of sOld within
' sValue, used for Mode 2 (segment replace). Regular VB String.Replace
' is case-sensitive, so this uses Regex instead - sOld is escaped so any
' regex-special characters in it are treated literally, and "$" in the
' replacement text is escaped so it can't be misread as a regex
' backreference.
Function ReplaceAllCaseInsensitive(sValue As String, sOld As String, sNew As String) As String
    Dim sPattern As String = System.Text.RegularExpressions.Regex.Escape(sOld)
    Dim sSafeNew As String = sNew.Replace("$", "$$")
    Return System.Text.RegularExpressions.Regex.Replace(sValue, sPattern, sSafeNew, System.Text.RegularExpressions.RegexOptions.IgnoreCase)
End Function


' Pre-built rename map for Mode 6 Copy Design (injected into Mode 2 multi-phase).
Function GetSetPrebuiltMode2Map(Optional bSet As Boolean = False, _
    Optional oNewVal As System.Collections.Generic.Dictionary(Of String, String) = Nothing) As System.Collections.Generic.Dictionary(Of String, String)
    Static oMap As System.Collections.Generic.Dictionary(Of String, String) = Nothing
    If bSet Then oMap = oNewVal
    Return oMap
End Function


' -----------------------------------------------------------------------
' Mode 6 history: persists across Inventor restarts via a small INI file
' in %TEMP% (CleanSweeper_Mode6History.ini), overwritten on every OK.
' In-session variables act as a fast cache so the file is only read once
' per Inventor session (first time the form opens).
' -----------------------------------------------------------------------
Private Shared g_sLastPrefix As String = ""
Private Shared g_sLastF1 As String = "" : Private Shared g_sLastR1 As String = ""
Private Shared g_sLastF2 As String = "" : Private Shared g_sLastR2 As String = ""
Private Shared g_sLastF3 As String = "" : Private Shared g_sLastR3 As String = ""
Private Shared g_sLastF4 As String = "" : Private Shared g_sLastR4 As String = ""
Private Shared g_sLastF5 As String = "" : Private Shared g_sLastR5 As String = ""
Private Shared g_bLastNonStd As Boolean = True
Private Shared g_bLastHonourFolder As Boolean = False   ' False = Clean single folder (default)
Private Shared g_bHistoryLoaded As Boolean = False      ' True once INI has been read this session

' Path to the persistent history file
Function Mode6HistoryFilePath() As String
    Return System.IO.Path.Combine(System.IO.Path.GetTempPath(), "CleanSweeper_Mode6History.ini")
End Function

' Read history from INI file into module-level variables (called once per session)
Sub LoadMode6History()
    Dim sPath As String = Mode6HistoryFilePath()
    If Not System.IO.File.Exists(sPath) Then Return
    Try
        Dim oLines() As String = System.IO.File.ReadAllLines(sPath)
        Dim oMap As New System.Collections.Generic.Dictionary(Of String, String)(System.StringComparer.OrdinalIgnoreCase)
        For Each sLine As String In oLines
            Dim iEq As Integer = sLine.IndexOf("="c)
            If iEq > 0 Then
                oMap(sLine.Substring(0, iEq).Trim()) = sLine.Substring(iEq + 1).Trim()
            End If
        Next
        Dim sVal As String = ""
        If oMap.TryGetValue("Prefix", sVal) Then g_sLastPrefix = sVal
        If oMap.TryGetValue("F1", sVal) Then g_sLastF1 = sVal
        If oMap.TryGetValue("R1", sVal) Then g_sLastR1 = sVal
        If oMap.TryGetValue("F2", sVal) Then g_sLastF2 = sVal
        If oMap.TryGetValue("R2", sVal) Then g_sLastR2 = sVal
        If oMap.TryGetValue("F3", sVal) Then g_sLastF3 = sVal
        If oMap.TryGetValue("R3", sVal) Then g_sLastR3 = sVal
        If oMap.TryGetValue("F4", sVal) Then g_sLastF4 = sVal
        If oMap.TryGetValue("R4", sVal) Then g_sLastR4 = sVal
        If oMap.TryGetValue("F5", sVal) Then g_sLastF5 = sVal
        If oMap.TryGetValue("R5", sVal) Then g_sLastR5 = sVal
        If oMap.TryGetValue("NonStd", sVal) Then g_bLastNonStd = (sVal = "1")
        If oMap.TryGetValue("HonourFolder", sVal) Then g_bLastHonourFolder = (sVal = "1")
    Catch
        ' Silently ignore any read errors — blank history is safe
    End Try
End Sub

' Write current history variables to the INI file
Sub SaveMode6History()
    Try
        Dim oLines As New System.Collections.Generic.List(Of String)
        oLines.Add("Prefix=" & g_sLastPrefix)
        oLines.Add("F1=" & g_sLastF1) : oLines.Add("R1=" & g_sLastR1)
        oLines.Add("F2=" & g_sLastF2) : oLines.Add("R2=" & g_sLastR2)
        oLines.Add("F3=" & g_sLastF3) : oLines.Add("R3=" & g_sLastR3)
        oLines.Add("F4=" & g_sLastF4) : oLines.Add("R4=" & g_sLastR4)
        oLines.Add("F5=" & g_sLastF5) : oLines.Add("R5=" & g_sLastR5)
        oLines.Add("NonStd=" & If(g_bLastNonStd, "1", "0"))
        oLines.Add("HonourFolder=" & If(g_bLastHonourFolder, "1", "0"))
        System.IO.File.WriteAllLines(Mode6HistoryFilePath(), oLines.ToArray())
    Catch
        ' Silently ignore write errors — history is a convenience, not critical
    End Try
End Sub

' Mode 6 secondary form: new project prefix, up to 5 segment pairs, non-std localize.
' Last-used values are pre-filled from the session-level history variables above.
Function ShowCopyDesignConfigForm(ByRef oChoice As RenameModeChoice, Optional sSourceAsmPath As String = "") As Boolean
    ' Load history from INI file on first call this session
    If Not g_bHistoryLoaded Then
        LoadMode6History()
        g_bHistoryLoaded = True
    End If

    Dim oForm As New Form()
    oForm.Text = "Copy Design - options (Vault-style)"
    oForm.StartPosition = FormStartPosition.CenterScreen
    oForm.TopMost = True
    oForm.FormBorderStyle = FormBorderStyle.FixedDialog
    oForm.MinimizeBox = False
    oForm.MaximizeBox = False
    oForm.Width = 560
    oForm.Height = 624  ' taller: 5 segment rows + history note + folder structure option + status label

    Dim oLblPrefix As New Label()
    oLblPrefix.Text = "New project prefix (applied to std AND non-std):"
    oLblPrefix.Left = 15 : oLblPrefix.Top = 15 : oLblPrefix.Width = 500
    oForm.Controls.Add(oLblPrefix)

    Dim oTxtPrefix As New System.Windows.Forms.TextBox()
    oTxtPrefix.Left = 15 : oTxtPrefix.Top = 38 : oTxtPrefix.Width = 500
    ' Pre-fill: prefer oChoice value (if caller pre-set it), else last-used history
    If Trim(oChoice.sReplace) <> "" Then
        oTxtPrefix.Text = oChoice.sReplace
    ElseIf Trim(g_sLastPrefix) <> "" Then
        oTxtPrefix.Text = g_sLastPrefix
    End If
    ' RE-RUN LOCK: if a previous copy of the GA already exists in the target folder,
    ' lock the prefix field so the user cannot accidentally use a different prefix.
    ' To use a different prefix, pick a fresh (empty) target folder.
    If oChoice.bPrefixLocked Then
        oTxtPrefix.Enabled = False
        oLblPrefix.Text = "New project prefix  [LOCKED - existing copy detected in target folder]:"
    End If
    oForm.Controls.Add(oTxtPrefix)

    Dim oLblSeg As New Label()
    oLblSeg.Text = "Optional segment replaces (up to 5) - applied AFTER prefix swap:"
    oLblSeg.Left = 15 : oLblSeg.Top = 75 : oLblSeg.Width = 500
    oForm.Controls.Add(oLblSeg)

    ' 5 Find/Replace row pairs (rows spaced 30px apart starting at top=100)
    Dim oTxtF1 As New System.Windows.Forms.TextBox() : oTxtF1.Left = 15 : oTxtF1.Top = 100 : oTxtF1.Width = 220
    Dim oTxtR1 As New System.Windows.Forms.TextBox() : oTxtR1.Left = 250 : oTxtR1.Top = 100 : oTxtR1.Width = 220
    Dim oTxtF2 As New System.Windows.Forms.TextBox() : oTxtF2.Left = 15 : oTxtF2.Top = 130 : oTxtF2.Width = 220
    Dim oTxtR2 As New System.Windows.Forms.TextBox() : oTxtR2.Left = 250 : oTxtR2.Top = 130 : oTxtR2.Width = 220
    Dim oTxtF3 As New System.Windows.Forms.TextBox() : oTxtF3.Left = 15 : oTxtF3.Top = 160 : oTxtF3.Width = 220
    Dim oTxtR3 As New System.Windows.Forms.TextBox() : oTxtR3.Left = 250 : oTxtR3.Top = 160 : oTxtR3.Width = 220
    Dim oTxtF4 As New System.Windows.Forms.TextBox() : oTxtF4.Left = 15 : oTxtF4.Top = 190 : oTxtF4.Width = 220
    Dim oTxtR4 As New System.Windows.Forms.TextBox() : oTxtR4.Left = 250 : oTxtR4.Top = 190 : oTxtR4.Width = 220
    Dim oTxtF5 As New System.Windows.Forms.TextBox() : oTxtF5.Left = 15 : oTxtF5.Top = 220 : oTxtF5.Width = 220
    Dim oTxtR5 As New System.Windows.Forms.TextBox() : oTxtR5.Left = 250 : oTxtR5.Top = 220 : oTxtR5.Width = 220

    Dim oLblArrow1 As New Label() : oLblArrow1.Text = "->" : oLblArrow1.Left = 238 : oLblArrow1.Top = 103 : oLblArrow1.Width = 20
    Dim oLblArrow2 As New Label() : oLblArrow2.Text = "->" : oLblArrow2.Left = 238 : oLblArrow2.Top = 133 : oLblArrow2.Width = 20
    Dim oLblArrow3 As New Label() : oLblArrow3.Text = "->" : oLblArrow3.Left = 238 : oLblArrow3.Top = 163 : oLblArrow3.Width = 20
    Dim oLblArrow4 As New Label() : oLblArrow4.Text = "->" : oLblArrow4.Left = 238 : oLblArrow4.Top = 193 : oLblArrow4.Width = 20
    Dim oLblArrow5 As New Label() : oLblArrow5.Text = "->" : oLblArrow5.Left = 238 : oLblArrow5.Top = 223 : oLblArrow5.Width = 20

    ' Pre-fill rows from history (will be overridden slot-by-slot by auto-detect below)
    oTxtF1.Text = g_sLastF1 : oTxtR1.Text = g_sLastR1
    oTxtF2.Text = g_sLastF2 : oTxtR2.Text = g_sLastR2
    oTxtF3.Text = g_sLastF3 : oTxtR3.Text = g_sLastR3
    oTxtF4.Text = g_sLastF4 : oTxtR4.Text = g_sLastR4
    oTxtF5.Text = g_sLastF5 : oTxtR5.Text = g_sLastR5

    ' ---- AUTO-DETECT SEGMENT ANOMALIES FROM FULL TREE ----
    ' Walks AllOccurrences (Vault-proof) + the GA folder for filenames that
    ' contain common convention problems. Suggestions fill the first rows.
    ' Examples caught:
    '   xx / -xx-           placeholder token
    '   -345-  vs -3450-    truncated / wrong equipment number
    '   PJ00xxx-PJyyyyy-    double prefix
    Dim iAutoCount As Integer = 0
    Dim oAutoFinds As New System.Collections.Generic.List(Of String)()
    Dim oAutoReplaces As New System.Collections.Generic.List(Of String)()

    Try
        Dim oSeenTokens As New System.Collections.Generic.HashSet(Of String)(StringComparer.OrdinalIgnoreCase)
        Dim oPathsToScan As New System.Collections.Generic.HashSet(Of String)(StringComparer.OrdinalIgnoreCase)

        ' Full-tree paths via AllOccurrences (preferred)
        Try
            If sSourceAsmPath <> "" Then
                Dim oActiveAsm As AssemblyDocument = Nothing
                Try
                    If ThisApplication.ActiveDocument IsNot Nothing AndAlso _
                       ThisApplication.ActiveDocument.DocumentType = kAssemblyDocumentObject Then
                        oActiveAsm = CType(ThisApplication.ActiveDocument, AssemblyDocument)
                    End If
                Catch : End Try
                If oActiveAsm IsNot Nothing Then
                    oPathsToScan.Add(oActiveAsm.FullFileName)
                    For Each oOcc As ComponentOccurrence In oActiveAsm.ComponentDefinition.AllOccurrences
                        Try
                            Dim sOccPath As String = oOcc.ReferencedFileDescriptor.FullDocumentName
                            If Trim(sOccPath) <> "" AndAlso Not sOccPath.Contains("*") Then oPathsToScan.Add(sOccPath)
                        Catch : End Try
                    Next
                End If
            End If
        Catch : End Try

        ' Also include immediate GA folder (fallback / drawings)
        If sSourceAsmPath <> "" AndAlso System.IO.File.Exists(sSourceAsmPath) Then
            Dim sSourceFolder As String = System.IO.Path.GetDirectoryName(sSourceAsmPath)
            Try
                For Each sFilePath As String In System.IO.Directory.GetFiles(sSourceFolder, "*.*")
                    Dim sExt As String = System.IO.Path.GetExtension(sFilePath).ToLower()
                    If sExt = ".ipt" OrElse sExt = ".iam" OrElse sExt = ".idw" OrElse sExt = ".dwg" Then
                        oPathsToScan.Add(sFilePath)
                    End If
                Next
            Catch : End Try
        End If

        Dim sGABase As String = ""
        Dim sCanonMiddle As String = ""   ' e.g. "-3450-6-"  (from first - to first V)
        If sSourceAsmPath <> "" AndAlso System.IO.File.Exists(sSourceAsmPath) Then
            sGABase = System.IO.Path.GetFileNameWithoutExtension(sSourceAsmPath)
            ' Extract canonical middle: from the first "-" after the project prefix
            ' up to (but not including) the first "V". Example:
            '   PJ00444-3450-6-V0-00  →  middle = "-3450-6-"
            Dim iFirstDash As Integer = sGABase.IndexOf("-"c)
            Dim iFirstV As Integer = sGABase.ToUpper().IndexOf("V")
            If iFirstDash > 0 AndAlso iFirstV > iFirstDash Then
                sCanonMiddle = sGABase.Substring(iFirstDash, iFirstV - iFirstDash)
                ' Ensure it ends with "-" for clean replacement
                If Not sCanonMiddle.EndsWith("-") Then sCanonMiddle = sCanonMiddle & "-"
            End If
        End If

        ' Count mismatched middle sections across the tree.
        ' Middle = from first "-" to first "V" (same rule as GA).
        Dim oMiddleCounts As New System.Collections.Generic.Dictionary(Of String, Integer)(StringComparer.OrdinalIgnoreCase)
        For Each sFilePath As String In oPathsToScan
            Dim sBase As String = System.IO.Path.GetFileNameWithoutExtension(sFilePath)
            Dim sBaseUp As String = sBase.ToUpper()

            ' Only consider proper project-convention names.
            ' Non-std parts (fasteners, library items, etc.) are excluded even if
            ' they later receive a PJ prefix. They do not follow PJ00XXX-XXXX-6-V.
            If Not sBaseUp.StartsWith("PJ") Then Continue For
            ' Skip obvious non-std / fastener / descriptive names
            If sBaseUp.Contains("GAL") OrElse sBaseUp.Contains("AS 11") OrElse _
               sBaseUp.Contains("AS 12") OrElse sBaseUp.Contains("DIN ") OrElse _
               sBaseUp.Contains("ISO ") OrElse sBaseUp.Contains("WASHER") OrElse _
               sBaseUp.Contains("NYLOCK") OrElse sBaseUp.Contains("SHACKLE") Then Continue For

            Dim iDash As Integer = sBase.IndexOf("-"c)
            Dim iV As Integer = sBaseUp.IndexOf("V")
            If iDash < 1 OrElse iV <= iDash Then Continue For
            Dim sMiddle As String = sBase.Substring(iDash, iV - iDash)
            If Not sMiddle.EndsWith("-") Then sMiddle = sMiddle & "-"
            ' Skip if it already matches the canonical middle
            If sCanonMiddle <> "" AndAlso String.Compare(sMiddle, sCanonMiddle, True) = 0 Then Continue For
            ' Skip very short or non-useful middles
            If sMiddle.Length < 3 Then Continue For
            ' Skip middles that do not look like a convention segment
            ' (must start with a digit or contain xx / another PJ)
            Dim sMidTrim As String = sMiddle.Trim("-"c)
            Dim bLooksLikeConvention As Boolean = False
            If sMidTrim.Length > 0 AndAlso Char.IsDigit(sMidTrim(0)) Then bLooksLikeConvention = True
            If sMiddle.ToUpper().Contains("XX") Then bLooksLikeConvention = True
            If sMiddle.ToUpper().Contains("-PJ") OrElse sMiddle.ToUpper().StartsWith("PJ") Then bLooksLikeConvention = True
            If Not bLooksLikeConvention Then Continue For

            ' Skip deliberate numeric variants when equipment number matches.
            ' Example: canonical "-3450-6-", file has "-3450-160-" → leave alone.
            ' Only flag if: contains "xx", equipment number differs, or double-prefix style.
            Dim bFlag As Boolean = False
            If sMiddle.ToUpper().Contains("XX") Then
                bFlag = True
            ElseIf sCanonMiddle <> "" Then
                ' Extract equipment token (first numeric segment after the leading -)
                Dim sCanonEq As String = ""
                Dim sMidEq As String = ""
                Dim sCanonParts() As String = sCanonMiddle.Trim("-"c).Split("-"c)
                Dim sMidParts() As String = sMiddle.Trim("-"c).Split("-"c)
                If sCanonParts.Length > 0 Then sCanonEq = sCanonParts(0)
                If sMidParts.Length > 0 Then sMidEq = sMidParts(0)
                ' Flag if equipment number is different, or if middle contains another PJ prefix
                If sCanonEq <> "" AndAlso String.Compare(sMidEq, sCanonEq, True) <> 0 Then
                    bFlag = True
                ElseIf sMiddle.ToUpper().Contains("-PJ") OrElse sMiddle.ToUpper().StartsWith("PJ") Then
                    bFlag = True
                End If
                ' Pure numeric variant with matching equipment number → do NOT flag
            End If
            If Not bFlag Then Continue For

            If oMiddleCounts.ContainsKey(sMiddle) Then
                oMiddleCounts(sMiddle) = oMiddleCounts(sMiddle) + 1
            Else
                oMiddleCounts(sMiddle) = 1
            End If
        Next

        ' Take mismatched middles. Double-prefix cases are always prioritised
        ' so they are not pushed out of the top 5 by more common but less important mismatches.
        Dim oSorted As New System.Collections.Generic.List(Of System.Collections.Generic.KeyValuePair(Of String, Integer))
        For Each kvp As System.Collections.Generic.KeyValuePair(Of String, Integer) In oMiddleCounts
            oSorted.Add(kvp)
        Next
        oSorted.Sort(Function(a, b)
                         Dim aDbl As Boolean = a.Key.ToUpper().Contains("-PJ") OrElse a.Key.ToUpper().StartsWith("PJ")
                         Dim bDbl As Boolean = b.Key.ToUpper().Contains("-PJ") OrElse b.Key.ToUpper().StartsWith("PJ")
                         If aDbl <> bDbl Then Return If(aDbl, -1, 1)
                         Return b.Value.CompareTo(a.Value)
                     End Function)
        Dim iAdded As Integer = 0
        For Each kvp As System.Collections.Generic.KeyValuePair(Of String, Integer) In oSorted
            If iAdded >= 5 Then Exit For
            If sCanonMiddle = "" Then Exit For
            If Not oSeenTokens.Contains(kvp.Key) Then
                oSeenTokens.Add(kvp.Key)
                oAutoFinds.Add(kvp.Key)
                oAutoReplaces.Add(sCanonMiddle)
                iAdded += 1
            End If
        Next
    Catch exAutoDetect As Exception
        ' Auto-detect is best-effort; any failure leaves history values in place
    End Try

    ' Merge auto-suggestions into text box slots.
    ' Slots 1..N get auto-detected pairs (highlighted yellow); remaining slots keep history.
    Dim oTxtFs() As System.Windows.Forms.TextBox = {oTxtF1, oTxtF2, oTxtF3, oTxtF4, oTxtF5}
    Dim oTxtRs() As System.Windows.Forms.TextBox = {oTxtR1, oTxtR2, oTxtR3, oTxtR4, oTxtR5}
    Dim oHistFs() As String = {g_sLastF1, g_sLastF2, g_sLastF3, g_sLastF4, g_sLastF5}
    Dim oHistRs() As String = {g_sLastR1, g_sLastR2, g_sLastR3, g_sLastR4, g_sLastR5}

    ' Fill auto-detect rows first
    For i As Integer = 0 To Math.Min(oAutoFinds.Count, 5) - 1
        oTxtFs(i).Text = oAutoFinds(i)
        oTxtRs(i).Text = oAutoReplaces(i)
        ' Note: System.Drawing.Color not available in iLogic sandbox — no BackColor tint
    Next
    iAutoCount = Math.Min(oAutoFinds.Count, 5)

    ' Fill remaining slots with history, skipping any already placed by auto-detect
    Dim iHistSlot As Integer = iAutoCount
    For h As Integer = 0 To 4
        If iHistSlot >= 5 Then Exit For
        If oHistFs(h) = "" Then Continue For
        Dim bDupe As Boolean = False
        For a As Integer = 0 To iAutoCount - 1
            If String.Compare(oTxtFs(a).Text, oHistFs(h), True) = 0 Then bDupe = True : Exit For
        Next
        If Not bDupe Then
            oTxtFs(iHistSlot).Text = oHistFs(h)
            oTxtRs(iHistSlot).Text = oHistRs(h)
            iHistSlot += 1
        End If
    Next

    Dim oLblHint As New Label()
    oLblHint.Text = "Find (left)  ->  Replace (right). Leave blank to skip a row." & vbCrLf & _
        "e.g.:  343-V0 -> 3431-6-V0     343-10 -> 3431-6-10     _ReferenceCopy -> _Duplicate"
    oLblHint.Left = 15 : oLblHint.Top = 252 : oLblHint.Width = 520 : oLblHint.Height = 36

    Dim oLblHistory As New Label()
    If iAutoCount > 0 Then
        oLblHistory.Text = "* Rows 1-" & iAutoCount & " AUTO-DETECTED (middle section vs GA). Remaining from last run."
    Else
        oLblHistory.Text = "* Fields pre-filled from last run this session."
    End If
    oLblHistory.Left = 15 : oLblHistory.Top = 290 : oLblHistory.Width = 520

    oForm.Controls.Add(oTxtF1) : oForm.Controls.Add(oTxtR1)
    oForm.Controls.Add(oTxtF2) : oForm.Controls.Add(oTxtR2)
    oForm.Controls.Add(oTxtF3) : oForm.Controls.Add(oTxtR3)
    oForm.Controls.Add(oTxtF4) : oForm.Controls.Add(oTxtR4)
    oForm.Controls.Add(oTxtF5) : oForm.Controls.Add(oTxtR5)
    oForm.Controls.Add(oLblArrow1) : oForm.Controls.Add(oLblArrow2)
    oForm.Controls.Add(oLblArrow3) : oForm.Controls.Add(oLblArrow4)
    oForm.Controls.Add(oLblArrow5)
    oForm.Controls.Add(oLblHint)
    oForm.Controls.Add(oLblHistory)

    Dim oChkNonStd As New CheckBox()
    oChkNonStd.Text = "Localize non-std parts (non-PJ names) into Non Std Parts with new prefix"
    oChkNonStd.Left = 15 : oChkNonStd.Top = 330 : oChkNonStd.Width = 520
    oChkNonStd.Checked = g_bLastNonStd
    oForm.Controls.Add(oChkNonStd)

    ' ---- DRAWING MODEL RENAME OPTION ----
    ' Height = 34 so the two-line wrap fits without clipping.
    Dim oChkKeepDwgNames As New CheckBox()
    oChkKeepDwgNames.Text = "Keep existing drawing model names (skip rename step — string rules still run on subs below)"
    oChkKeepDwgNames.Left = 15 : oChkKeepDwgNames.Top = 355 : oChkKeepDwgNames.Width = 520 : oChkKeepDwgNames.Height = 34
    oChkKeepDwgNames.Checked = False   ' default OFF: show rename form
    oForm.Controls.Add(oChkKeepDwgNames)

    ' ---- FOLDER STRUCTURE OPTIONS ----
    ' Top pushed down to 397 (355 + 34 + 8 gap) so it clears the checkbox.
    Dim oGrpFolder As New GroupBox()
    oGrpFolder.Text = "FOLDER STRUCTURE"
    oGrpFolder.Left = 15 : oGrpFolder.Top = 397 : oGrpFolder.Width = 520 : oGrpFolder.Height = 92
    oForm.Controls.Add(oGrpFolder)

    Dim oRbClean As New RadioButton()
    oRbClean.Text = "1. CLEAN SINGLE FOLDER  — all files land flat in target folder  (default)"
    oRbClean.Left = 8 : oRbClean.Top = 14 : oRbClean.Width = 500
    oGrpFolder.Controls.Add(oRbClean)

    Dim oRbHonour As New RadioButton()
    oRbHonour.Text = "2. HONOUR EXISTING  — files keep their relative sub-folder path inside target"
    oRbHonour.Left = 8 : oRbHonour.Top = 38 : oRbHonour.Width = 500
    oGrpFolder.Controls.Add(oRbHonour)

    ' Live status label — shows which option is currently selected (hard to miss)
    Dim oLblFolderStatus As New Label()
    oLblFolderStatus.Left = 8 : oLblFolderStatus.Top = 66 : oLblFolderStatus.Width = 500 : oLblFolderStatus.Height = 18
    ' iLogic sandbox: System.Drawing.Font constructor is blocked — use control Tag to carry bold marker
    ' and prefix the text with ">> ACTIVE:" which is visually distinct enough without bold.
    oGrpFolder.Controls.Add(oLblFolderStatus)

    ' Helper to refresh the status label
    Dim oFolderStatusRefresh As Action = Sub()
        If oRbHonour.Checked Then
            oLblFolderStatus.Text = ">> ACTIVE: HONOUR EXISTING — sub-folders will be preserved"
        Else
            oLblFolderStatus.Text = ">> ACTIVE: CLEAN SINGLE FOLDER — all files flattened to target"
        End If
    End Sub

    AddHandler oRbClean.CheckedChanged, Sub(s, e) oFolderStatusRefresh()
    AddHandler oRbHonour.CheckedChanged, Sub(s, e) oFolderStatusRefresh()

    ' Pre-select from history
    If g_bLastHonourFolder Then
        oRbHonour.Checked = True
    Else
        oRbClean.Checked = True
    End If
    oFolderStatusRefresh()   ' set label to match pre-selection

    Dim oLblNote As New Label()
    oLblNote.Text = "Next: scan tree for old P-prefixes to swap. One map, one pass."
    oLblNote.Left = 15 : oLblNote.Top = 498 : oLblNote.Width = 500
    oForm.Controls.Add(oLblNote)

    ' Drawing Update section removed 2026-10-28:
    ' Drawing update is always ON in this rule (auto-detected from the open GA drawing).
    ' The folder is auto-set from ThisDoc.FullFileName before this form is shown.
    ' No checkbox or folder browse needed here.

    oForm.Height = 594

    Dim oOk As New Button()
    oOk.Text = "OK" : oOk.DialogResult = DialogResult.OK
    oOk.Left = 350 : oOk.Top = 529 : oOk.Width = 90
    oForm.Controls.Add(oOk) : oForm.AcceptButton = oOk

    Dim oCancel As New Button()
    oCancel.Text = "Cancel" : oCancel.DialogResult = DialogResult.Cancel
    oCancel.Left = 450 : oCancel.Top = 529 : oCancel.Width = 90
    oForm.Controls.Add(oCancel) : oForm.CancelButton = oCancel

    If oForm.ShowDialog() <> DialogResult.OK Then Return False

    Dim sPrefix As String = Trim(oTxtPrefix.Text)
    If sPrefix = "" Then
        MessageBox.Show("New project prefix is required.", "Copy Design")
        Return False
    End If

    ' Save to history variables and persist to INI file for next Inventor session
    g_sLastPrefix = sPrefix
    g_sLastF1 = Trim(oTxtF1.Text) : g_sLastR1 = Trim(oTxtR1.Text)
    g_sLastF2 = Trim(oTxtF2.Text) : g_sLastR2 = Trim(oTxtR2.Text)
    g_sLastF3 = Trim(oTxtF3.Text) : g_sLastR3 = Trim(oTxtR3.Text)
    g_sLastF4 = Trim(oTxtF4.Text) : g_sLastR4 = Trim(oTxtR4.Text)
    g_sLastF5 = Trim(oTxtF5.Text) : g_sLastR5 = Trim(oTxtR5.Text)
    g_bLastNonStd = oChkNonStd.Checked
    g_bLastHonourFolder = oRbHonour.Checked
    SaveMode6History()   ' write to %TEMP%\CleanSweeper_Mode6History.ini

    oChoice.sReplace = sPrefix
    oChoice.bLocalizeNonStd = oChkNonStd.Checked
    oChoice.bHonourFolderStructure = oRbHonour.Checked
    oChoice.bKeepDrawingModelNames = oChkKeepDwgNames.Checked
    ' bUpdateDrawings and sDrawingsFolder are set before this form opens (auto-detected
    ' from the open GA drawing in Sub Main) — not captured here.
    ' sTargetFolder is set by the dedicated folder-selection step BEFORE this
    ' form opens (Step 1 in Sub Main) — not captured here.
    oChoice.oSegFinds.Clear()
    oChoice.oSegReplaces.Clear()
    If Trim(oTxtF1.Text) <> "" Then
        oChoice.oSegFinds.Add(Trim(oTxtF1.Text))
        oChoice.oSegReplaces.Add(Trim(oTxtR1.Text))
    End If
    If Trim(oTxtF2.Text) <> "" Then
        oChoice.oSegFinds.Add(Trim(oTxtF2.Text))
        oChoice.oSegReplaces.Add(Trim(oTxtR2.Text))
    End If
    If Trim(oTxtF3.Text) <> "" Then
        oChoice.oSegFinds.Add(Trim(oTxtF3.Text))
        oChoice.oSegReplaces.Add(Trim(oTxtR3.Text))
    End If
    If Trim(oTxtF4.Text) <> "" Then
        oChoice.oSegFinds.Add(Trim(oTxtF4.Text))
        oChoice.oSegReplaces.Add(Trim(oTxtR4.Text))
    End If
    If Trim(oTxtF5.Text) <> "" Then
        oChoice.oSegFinds.Add(Trim(oTxtF5.Text))
        oChoice.oSegReplaces.Add(Trim(oTxtR5.Text))
    End If
    Return True
End Function


' Build one master rename map for Mode 6:
' 1) old-prefix -> new prefix (starts-with)
' 2) optional segment replaces (contains)
' 3) non-std localization into Non Std Parts\NewPrefix_Name
' 4) folder routing: flat (bHonourFolderStructure=False) or preserve relative path (True)
Function BuildCopyDesignRenameMap(oAsmDoc As AssemblyDocument, _
    oOldPrefixes As System.Collections.Generic.List(Of String), _
    sNewPrefix As String, _
    oSegFinds As System.Collections.Generic.List(Of String), _
    oSegReplaces As System.Collections.Generic.List(Of String), _
    bLocalizeNonStd As Boolean, _
    bHonourFolderStructure As Boolean, _
    sTargetFolder As String, _
    sTopAssemblyFullName As String, _
    sNonStdFolder As String, _
    oTier1Map As System.Collections.Generic.Dictionary(Of String, String), _
    oLog As System.Text.StringBuilder, _
    sLogFilePath As String) As System.Collections.Generic.Dictionary(Of String, String)

    Dim oMap As New System.Collections.Generic.Dictionary(Of String, String)(StringComparer.OrdinalIgnoreCase)
    Dim oAllDocs As New System.Collections.Generic.List(Of Document)
    oAllDocs.Add(oAsmDoc)
    ' AllReferencedDocuments throws E_FAIL when Inventor can't resolve the full
    ' reference chain (e.g. a previous partial run left a broken ref tree).
    ' Fall back to scanning all currently open documents in the session.
    Try
        For Each oRefDoc As Document In oAsmDoc.AllReferencedDocuments
            Try : oAllDocs.Add(oRefDoc) : Catch : End Try
        Next
    Catch exAllRef As Exception
        Try : System.IO.File.AppendAllText(sLogFilePath, "WARNING: AllReferencedDocuments failed (" & exAllRef.Message & ") - falling back to open Documents collection." & vbCrLf) : Catch : End Try
        For Each oFbDoc As Document In ThisApplication.Documents
            Try
                If oFbDoc IsNot Nothing AndAlso Not oAllDocs.Contains(oFbDoc) Then oAllDocs.Add(oFbDoc)
            Catch : End Try
        Next
    End Try

    Dim oExtraPaths As New System.Collections.Generic.HashSet(Of String)(StringComparer.OrdinalIgnoreCase)
    For Each oDoc As Document In oAllDocs
        Try
            If oDoc.DocumentType <> kAssemblyDocumentObject AndAlso _
               oDoc.DocumentType <> kPartDocumentObject Then Continue For
            For Each oFD As FileDescriptor In oDoc.File.ReferencedFileDescriptors
                Dim sExtra As String = ""
                Try : sExtra = oFD.FullFileName : Catch : Continue For : End Try
                If Trim(sExtra) = "" OrElse sExtra.Contains("*") Then Continue For
                oExtraPaths.Add(sExtra)
            Next
        Catch
        End Try
    Next

    Dim oCandidatePaths As New System.Collections.Generic.List(Of String)
    For Each oDoc As Document In oAllDocs
        Try
            Dim sP As String = oDoc.FullFileName
            If Trim(sP) <> "" AndAlso Not sP.Contains("*") Then oCandidatePaths.Add(sP)
        Catch
        End Try
    Next
    For Each sExtra As String In oExtraPaths
        oCandidatePaths.Add(sExtra)
    Next

    Dim iMapped As Integer = 0
    Dim iSkipped As Integer = 0

    For Each sOldFull As String In oCandidatePaths
        Try
            If Trim(sOldFull) = "" OrElse sOldFull.Contains("*") Then Continue For
            If String.Compare(sOldFull, sTopAssemblyFullName, True) = 0 Then Continue For
            If IsInExcludedFolder(sOldFull) Then Continue For
            If oMap.ContainsKey(sOldFull) Then Continue For
            Dim bOutsideTarget As Boolean = Not IsDocSafeToMutate(sOldFull, sTargetFolder, sTopAssemblyFullName)
            If bOutsideTarget Then
                ' Files outside the target tree are allowed into the map only if they
                ' match an old prefix (they need pulling into the target folder) OR if
                ' non-std localization is on (non-PJ files get routed to Non Std Parts).
                ' Pure library / excluded files are already filtered above.
                ' We check prefix match below; skip now only if neither condition can apply.
                If Not bLocalizeNonStd Then
                    ' Still include if it matches an old prefix — we need to relocate it.
                    Dim bHasOldPrefix As Boolean = False
                    If oOldPrefixes IsNot Nothing Then
                        For Each sTmp As String In oOldPrefixes
                            If Trim(sTmp) <> "" AndAlso System.IO.Path.GetFileNameWithoutExtension(sOldFull).ToUpper().StartsWith(sTmp.ToUpper()) Then
                                bHasOldPrefix = True : Exit For
                            End If
                        Next
                    End If
                    If Not bHasOldPrefix Then Continue For
                End If
            End If

            Dim sOldName As String = System.IO.Path.GetFileNameWithoutExtension(sOldFull)
            Dim sExt As String = System.IO.Path.GetExtension(sOldFull)
            Dim sNewName As String = sOldName
            Dim bChanged As Boolean = False
            Dim bNonStdTarget As Boolean = False

            ' TIER-1 GUARD: if this model was explicitly renamed (or locked) in the
            ' drawing model rename form, use that name directly and skip ALL string rules.
            ' This ensures drawing-referenced model names are never touched by prefix swap
            ' or segment rules — the user's explicit decision is the final word.
            If oTier1Map IsNot Nothing AndAlso oTier1Map.ContainsKey(sOldName) Then
                Dim sTier1New As String = oTier1Map(sOldName)
                Dim sT1DestDir As String = sTargetFolder
                Dim sT1NewFull As String = ""
                If String.Compare(sTier1New, sOldName, True) <> 0 Then
                    ' Explicit rename - compute destination and add to map
                    sT1NewFull = System.IO.Path.Combine(sT1DestDir, sTier1New & sExt)
                    If Not oMap.ContainsKey(sOldFull) Then
                        oMap(sOldFull) = sT1NewFull
                        Try : System.IO.File.AppendAllText(sLogFilePath, "TIER1-RENAME: " & sOldName & " -> " & sTier1New & vbCrLf) : Catch : End Try
                    End If
                Else
                    ' Locked (keep existing name) — still needs to land in target folder
                    sT1NewFull = System.IO.Path.Combine(sT1DestDir, sOldName & sExt)
                    If Not oMap.ContainsKey(sOldFull) AndAlso String.Compare(sOldFull, sT1NewFull, True) <> 0 Then
                        oMap(sOldFull) = sT1NewFull
                        Try : System.IO.File.AppendAllText(sLogFilePath, "TIER1-LOCK: " & sOldName & " (relocate only)" & vbCrLf) : Catch : End Try
                    End If
                End If
                Continue For   ' skip all string rules for this file
            End If

            ' 1) Prefix swap (longest matching old prefix first)
            Dim sMatchedOld As String = ""
            If oOldPrefixes IsNot Nothing Then
                For Each sOP As String In oOldPrefixes
                    If Trim(sOP) = "" Then Continue For
                    If sNewName.ToUpper().StartsWith(sOP.ToUpper()) Then
                        If sMatchedOld = "" OrElse sOP.Length > sMatchedOld.Length Then sMatchedOld = sOP
                    End If
                Next
            End If
            If sMatchedOld <> "" AndAlso String.Compare(sMatchedOld, sNewPrefix, True) <> 0 Then
                sNewName = sNewPrefix & sNewName.Substring(sMatchedOld.Length)
                bChanged = True
            End If

            ' 2) Segment replaces in order
            If oSegFinds IsNot Nothing Then
                Dim iSeg As Integer
                For iSeg = 0 To oSegFinds.Count - 1
                    Dim sSF As String = oSegFinds(iSeg)
                    Dim sSR As String = ""
                    If oSegReplaces IsNot Nothing AndAlso iSeg < oSegReplaces.Count Then sSR = oSegReplaces(iSeg)
                    If Trim(sSF) = "" Then Continue For
                    If sNewName.ToUpper().Contains(sSF.ToUpper()) Then
                        sNewName = Trim(ReplaceAllCaseInsensitive(sNewName, sSF, sSR)).Replace("_ ", "_").Replace("  ", " ")
                        Do While sNewName.Contains("__")
                            sNewName = sNewName.Replace("__", "_")
                        Loop
                        sNewName = sNewName.Trim("_"c).Trim()
                        bChanged = True
                    End If
                Next
            End If

            ' 2b) Strip "Copy of " prefix added by Vault's Copy Design operation.
            '     This runs AFTER user segment replaces so user overrides still win,
            '     but BEFORE the non-std check so a "Copy of PJ00143-..." file is
            '     correctly recognised as a PJ part and lands in the main folder.
            If sNewName.ToUpper().StartsWith("COPY OF ") Then
                sNewName = sNewName.Substring(8).Trim()  ' remove "Copy of " (8 chars)
                sNewName = sNewName.Trim("_"c).Trim()
                bChanged = True
            End If

            ' 3) Non-std: name does not start with PJ AFTER all transforms above.
            '    Use sNewName here (not sOldName) so that a segment replace which
            '    stripped a leading "OBSOLETE_" and left a clean PJ-prefixed result
            '    is NOT re-prefixed a second time by this block.
            Dim bIsNonStdAfterTransform As Boolean = Not sNewName.ToUpper().StartsWith("PJ")
            If bLocalizeNonStd AndAlso bIsNonStdAfterTransform Then
                ' Prefix with new project number if not already
                If Not sNewName.ToUpper().StartsWith(sNewPrefix.ToUpper()) Then
                    sNewName = sNewPrefix & "_" & sNewName
                End If
                bNonStdTarget = True
                bChanged = True
            End If

            If Not bChanged OrElse sNewName = "" OrElse String.Compare(sNewName, sOldName, True) = 0 Then
                ' Non-std still needs folder move even if name already has prefix
                If bLocalizeNonStd AndAlso bIsNonStdAfterTransform Then
                    bNonStdTarget = True
                    If Not sNewName.ToUpper().StartsWith(sNewPrefix.ToUpper()) Then
                        sNewName = sNewPrefix & "_" & sNewName
                    End If
                ElseIf bOutsideTarget Then
                    ' File outside target with unchanged name — still relocate it
                    ' (bChanged stays False but sDestDir will differ, so map entry is valid)
                Else
                    iSkipped = iSkipped + 1
                    Continue For
                End If
            End If

            ' Files outside the target tree are relocated INTO it.
            ' Non-std files go to Non Std Parts; PJ-prefixed files go to the main target folder.
            ' Also: a PJ-prefixed file currently sitting in Non Std Parts is promoted to the
            ' main target folder (it was mis-routed by a previous run).
            Dim sCurrentDir As String = System.IO.Path.GetDirectoryName(sOldFull)
            Dim bInNonStdFolder As Boolean = (Trim(sNonStdFolder) <> "" AndAlso
                String.Compare(sCurrentDir, sNonStdFolder, True) = 0)
            Dim sDestDir As String
            If bNonStdTarget AndAlso Trim(sNonStdFolder) <> "" Then
                ' Non-std parts always go to Non Std Parts regardless of folder mode.
                sDestDir = sNonStdFolder
            ElseIf bOutsideTarget Then
                ' File is outside the target tree — relocate into it.
                If bHonourFolderStructure Then
                    ' HONOUR EXISTING: preserve the immediate subfolder name.
                    Dim sRelative As String = ""
                    Try
                        sRelative = System.IO.Path.GetFileName(sCurrentDir)
                    Catch
                    End Try
                    If Trim(sRelative) <> "" Then
                        sDestDir = System.IO.Path.Combine(sTargetFolder, sRelative)
                    Else
                        sDestDir = sTargetFolder
                    End If
                Else
                    ' CLEAN SINGLE FOLDER: flatten into target folder.
                    sDestDir = sTargetFolder
                End If
            ElseIf bInNonStdFolder AndAlso Not bIsNonStdAfterTransform Then
                ' PJ-prefixed file sitting in Non Std Parts — decide whether to promote.
                ' Standard project parts use a hyphen immediately after the prefix number
                ' (e.g. PJ00143-3431-6-V0-...) whereas non-std parts localised by a
                ' previous run use an underscore (e.g. PJ00143_JC002135).
                ' Promote to main folder only when the separator is "-".
                Dim sPrefixLen As Integer = sNewPrefix.Length   ' e.g. 7 for "PJ00143"
                Dim bHyphenSep As Boolean = (sNewName.Length > sPrefixLen AndAlso
                    sNewName(sPrefixLen) = "-"c)
                If bHyphenSep Then
                    sDestDir = sTargetFolder   ' genuine project part — promote
                Else
                    sDestDir = sCurrentDir     ' non-std (underscore separator) — keep in Non Std Parts
                End If
            ElseIf bHonourFolderStructure AndAlso Not bInNonStdFolder Then
                ' HONOUR EXISTING: file is already inside the target tree — keep its subfolder.
                sDestDir = sCurrentDir
            Else
                ' CLEAN SINGLE FOLDER (default): flatten everything into the target folder.
                sDestDir = sTargetFolder
            End If
            Dim sNewFull As String = System.IO.Path.Combine(sDestDir, sNewName & sExt)
            If String.Compare(sOldFull, sNewFull, True) = 0 Then
                iSkipped = iSkipped + 1
                Continue For
            End If

            ' COLLISION GUARD (safe mode):
            ' If the computed target name already exists on disk OR is already
            ' claimed by another source in this same map, always take the next
            ' free sequence number. No geometry check.
            Dim bNeedNextNumber As Boolean = False
            If String.Compare(sOldFull, sNewFull, True) <> 0 Then
                If System.IO.File.Exists(sNewFull) Then bNeedNextNumber = True
                ' Also claimed by an earlier entry in this map?
                For Each sClaimed As String In oMap.Values
                    If String.Compare(sClaimed, sNewFull, True) = 0 Then
                        bNeedNextNumber = True
                        Exit For
                    End If
                Next
            End If

            If bNeedNextNumber Then
                ' Build a set of already-claimed target names so the next-number
                ' search sees both files on disk AND names claimed earlier in this map.
                Dim oClaimed As New System.Collections.Generic.HashSet(Of String)(StringComparer.OrdinalIgnoreCase)
                For Each sClaimed As String In oMap.Values
                    oClaimed.Add(sClaimed)
                Next
                Dim sNextName As String = NextFreeSequenceName(sDestDir, sNewName, sExt, oClaimed)
                ' Keep asking until we get a name that is free on disk and not claimed
                Dim iGuard As Integer = 0
                Do While sNextName <> "" AndAlso iGuard < 30
                    Dim sTryFull As String = System.IO.Path.Combine(sDestDir, sNextName & sExt)
                    Dim bTaken As Boolean = System.IO.File.Exists(sTryFull) OrElse oClaimed.Contains(sTryFull)
                    If Not bTaken Then Exit Do
                    oClaimed.Add(sTryFull)
                    sNextName = NextFreeSequenceName(sDestDir, sNextName, sExt, oClaimed)
                    iGuard += 1
                Loop
                If sNextName <> "" Then
                    sNewName = sNextName
                    sNewFull = System.IO.Path.Combine(sDestDir, sNewName & sExt)
                    Try : System.IO.File.AppendAllText(sLogFilePath, "COLLISION: " & System.IO.Path.GetFileName(sOldFull) & " -> " & sNewName & sExt & " (next free sequence)" & vbCrLf) : Catch : End Try
                    oLog.Append(vbCrLf & "  COLLISION (next sequence): " & System.IO.Path.GetFileName(sOldFull) & " -> " & sNewName & sExt)
                End If
            End If

            oMap(sOldFull) = sNewFull
            iMapped = iMapped + 1
        Catch
            iSkipped = iSkipped + 1
        End Try
    Next

    oLog.Append(vbCrLf & "Copy Design map: " & iMapped & " rename(s), " & iSkipped & " skipped.")
    Try : System.IO.File.AppendAllText(sLogFilePath, "Copy Design map: " & iMapped & " rename(s), " & iSkipped & " skipped." & vbCrLf) : Catch : End Try
    Return oMap
End Function


' Processes one level of the tree (a ComponentDefinition belonging to either
' the main assembly or a sub-assembly). Returns True if this level's own
' occurrence list was modified (i.e. one of its direct children got renamed),
' so the caller knows whether IT needs to re-save itself.


' Determines where a matching sub's NEW copy should actually be saved.
' Normally that's just sMainTargetFolder (the current assembly's own
' folder). But if the sub's CURRENT immediate parent folder is literally
' named "Non Std Parts" - regardless of which project's path it's under -
' its new copy is routed into THIS assembly's own "Non Std Parts"
' sub-folder instead, preserving the non-standard/GA organizational
' split across the relocation rather than mixing it back into the main
' folder. The folder is created if it doesn't already exist.
' Returns the folder where a file should land in the target location.
' Three cases handled:
'
' 1. Non Std Parts subfolder: always maps to <target>\Non Std Parts\.
'
' 2. File lives in a subfolder of the original Models root (i.e. the
'    parent of sMainTargetFolder, since the target folder is always a
'    subfolder of the original Models folder, e.g.:
'      Original root: ...\Models\
'      Target:        ...\Models\184 TEST - Models\
'      File:          ...\Models\PJ00184-V02-01\Frame\Part.ipt
'    The relative path \PJ00184-V02-01\Frame\ is mirrored under target:
'      Result:        ...\Models\184 TEST - Models\PJ00184-V02-01\Frame\
'    This handles Inventor Frame Generator members and any other files
'    that Inventor places in named subfolders under the Models folder.
'
' 3. Everything else (file already flat in the original Models root, or
'    in a completely different location): goes flat into sMainTargetFolder.
Function GetEffectiveTargetFolder(sOldFullName As String, sMainTargetFolder As String) As String

    Dim sParentFolderName As String = System.IO.Path.GetFileName(System.IO.Path.GetDirectoryName(sOldFullName))
    Dim sFileFolder As String = System.IO.Path.GetDirectoryName(sOldFullName)

    ' Case 1: Non Std Parts.
    If String.Compare(sParentFolderName, "Non Std Parts", True) = 0 Then
        Dim sNonStdFolder As String = System.IO.Path.Combine(sMainTargetFolder, "Non Std Parts")
        Try
            If Not System.IO.Directory.Exists(sNonStdFolder) Then System.IO.Directory.CreateDirectory(sNonStdFolder)
        Catch
            Return sMainTargetFolder
        End Try
        Return sNonStdFolder
    End If

    ' Case 2: File in a subfolder of the original Models root.
    ' The original root is the parent of sMainTargetFolder (since target
    ' is always a subfolder of original: ...\Models\184 TEST - Models\).
    Try
        Dim sOriginalRoot As String = System.IO.Path.GetDirectoryName(sMainTargetFolder.TrimEnd(System.IO.Path.DirectorySeparatorChar))
        If sOriginalRoot <> "" Then
            Dim sFileFolderU As String = sFileFolder.TrimEnd(System.IO.Path.DirectorySeparatorChar).ToUpper()
            Dim sOriginalRootU As String = sOriginalRoot.TrimEnd(System.IO.Path.DirectorySeparatorChar).ToUpper()
            If sFileFolderU.StartsWith(sOriginalRootU & System.IO.Path.DirectorySeparatorChar) Then
                Dim sRelative As String = sFileFolder.Substring(sOriginalRoot.Length + 1).TrimEnd(System.IO.Path.DirectorySeparatorChar)
                ' sRelative is now e.g. "PJ00184-3250-00-01-V02-01\Frame"
                ' Don't mirror if sRelative is empty (file is flat in original root)
                ' or if it starts with the target folder name (file is already inside the target).
                Dim sTargetFolderName As String = System.IO.Path.GetFileName(sMainTargetFolder.TrimEnd(System.IO.Path.DirectorySeparatorChar))
                If sRelative <> "" AndAlso Not sRelative.ToUpper().StartsWith(sTargetFolderName.ToUpper()) Then
                    Dim sMirroredFolder As String = System.IO.Path.Combine(sMainTargetFolder, sRelative)
                    Try
                        If Not System.IO.Directory.Exists(sMirroredFolder) Then System.IO.Directory.CreateDirectory(sMirroredFolder)
                        Return sMirroredFolder
                    Catch
                        ' Fall through to flat copy if subfolder creation fails.
                    End Try
                End If
            End If
        End If
    Catch
        ' Fall through on any error.
    End Try

    ' Case 3: flat into main target folder.
    Return sMainTargetFolder

End Function


' ---------------------------------------------------------------------
' PRE-SCAN: read-only tree walk that reports the status of every file
' found under oCompDef, without copying, renaming or repointing anything.
' Writes directly to sReportPath as it goes (so you get a partial report
' even if Inventor crashes mid-scan). iDepth controls indentation so the
' tree structure is visible in the output file.
'
' STATUS for each distinct file:
'   [NEEDS COPY]    - starts with Find prefix, outside target folder
'   [ALREADY LOCAL] - starts with Find prefix, already in correct folder
'   [NO PREFIX]     - doesn't match Find prefix (not a consolidation target)
'   [EXCLUDED]      - inside an always-skipped folder
'   [SUPPRESSED]    - suppressed occurrence (definition not loaded)
'   [VIRTUAL]       - virtual/embedded component, no independent file
'
' Each distinct file is only reported once at the depth where it is first
' encountered (oPreScanVisited gate). Suppressed occurrences are noted
' at the level where they're found (can't get their full path).
' ---------------------------------------------------------------------
Sub PreScanLevel(oCompDef As ComponentDefinition, sFind As String, sTargetFolder As String, sReportPath As String, iDepth As Integer, ByRef oPreScanVisited As System.Collections.Generic.HashSet(Of String), ByRef iTotal As Integer, ByRef iNeedsCopy As Integer, ByRef iAlreadyLocal As Integer, ByRef iExcluded As Integer, ByRef iSuppressed As Integer, ByRef iNoPrefix As Integer, ByRef iVirtual As Integer)

    Dim sIndent As String = New String(" "c, iDepth * 2)
    Dim sParentName As String = System.IO.Path.GetFileName(oCompDef.Document.FullFileName)

    For Each oOcc As ComponentOccurrence In oCompDef.Occurrences

        ' Suppressed occurrences are still processed - the suppression is a
        ' model-state flag, not a deleted reference. If a model state change
        ' or manual unsuppress activates it later, it must resolve locally.
        ' We tag it [SUPPRESSED] in the report so it's distinguishable.
        Dim sSuppressedTag As String = If(oOcc.Suppressed, " [SUPPRESSED]", "")

        Dim oRefDoc As Document = Nothing
        Dim sFull As String = ""
        Try
            oRefDoc = oOcc.Definition.Document
            sFull = oRefDoc.FullFileName
        Catch
            ' Definition.Document throws for suppressed occurrences whose
            ' definition isn't loaded. Try ReferencedFileDescriptor to get
            ' the path without needing the definition loaded in memory.
            Try
                sFull = oOcc.ReferencedFileDescriptor.FullFileName
            Catch
                sFull = ""
            End Try
            If sFull = "" OrElse sFull.Contains("*") OrElse Not System.IO.File.Exists(sFull) Then
                iVirtual = iVirtual + 1
                Try
                    System.IO.File.AppendAllText(sReportPath, sIndent & "[VIRTUAL]       " & oOcc.Name & "  (no document accessible)" & sSuppressedTag & vbCrLf)
                Catch
                End Try
                Continue For
            End If
            ' Got a real path via ReferencedFileDescriptor - oRefDoc stays
            ' Nothing but sFull is valid; fall through to normal processing.
        End Try

        If Trim(sFull) = "" OrElse sFull.Contains("*") OrElse IsSyntheticPatternMemberName(sFull) OrElse String.Compare(sFull, oCompDef.Document.FullFileName, True) = 0 Then
            iVirtual = iVirtual + 1
            Try
                System.IO.File.AppendAllText(sReportPath, sIndent & "[VIRTUAL]       " & oOcc.Name & "  [" & System.IO.Path.GetFileName(sFull) & "]" & sSuppressedTag & vbCrLf)
            Catch
            End Try
            Continue For
        End If

        Dim sKey As String = sFull.ToUpper()
        Dim bAlreadySeen As Boolean = oPreScanVisited.Contains(sKey)
        If Not bAlreadySeen Then oPreScanVisited.Add(sKey)

        Dim sFileNameNoExt As String = System.IO.Path.GetFileNameWithoutExtension(sFull)
        Dim sCurrentFolder As String = System.IO.Path.GetDirectoryName(sFull)
        Dim sEffectiveTarget As String = GetEffectiveTargetFolder(sFull, sTargetFolder)

        Dim sStatus As String
        Dim sDetail As String = ""

        If IsInExcludedFolder(sFull) Then
            sStatus = "[EXCLUDED]     "
            If Not bAlreadySeen Then iExcluded = iExcluded + 1
        ElseIf IsContentCenterMember(oRefDoc) Then
            sStatus = "[EXCLUDED CC]  "
            If Not bAlreadySeen Then iExcluded = iExcluded + 1
        ElseIf Not sFileNameNoExt.ToUpper().StartsWith(sFind.ToUpper()) Then
            sStatus = "[NO PREFIX]    "
            If Not bAlreadySeen Then iNoPrefix = iNoPrefix + 1
        ElseIf String.Compare(sCurrentFolder, sEffectiveTarget, True) = 0 Then
            sStatus = "[ALREADY LOCAL]"
            If Not bAlreadySeen Then iAlreadyLocal = iAlreadyLocal + 1
        Else
            sStatus = "[NEEDS COPY]   "
            sDetail = "  FROM: " & sCurrentFolder
            If Not bAlreadySeen Then iNeedsCopy = iNeedsCopy + 1
        End If

        If Not bAlreadySeen Then
            iTotal = iTotal + 1
        End If
        ' Count suppressed occurrences regardless of dedup - every suppressed
        ' occurrence is worth knowing about even if the same file is also
        ' placed unsuppressed elsewhere (which would make bAlreadySeen=True).
        If oOcc.Suppressed Then iSuppressed = iSuppressed + 1

        Dim sSeenNote As String = If(bAlreadySeen, "  (shared - already counted above)", "")

        Try
            System.IO.File.AppendAllText(sReportPath, sIndent & sStatus & "  " & sFull & sDetail & sSuppressedTag & sSeenNote & vbCrLf)
        Catch
        End Try

        ' Recurse into sub-assemblies (using the ORIGINAL doc, read-only -
        ' this is a scan only, no copies are made here).
        If Not bAlreadySeen AndAlso oRefDoc.DocumentType = kAssemblyDocumentObject Then
            Try
                PreScanLevel(oRefDoc.ComponentDefinition, sFind, sTargetFolder, sReportPath, iDepth + 1, oPreScanVisited, iTotal, iNeedsCopy, iAlreadyLocal, iExcluded, iSuppressed, iNoPrefix, iVirtual)
            Catch ex As Exception
                Try
                    System.IO.File.AppendAllText(sReportPath, sIndent & "  [ERROR recursing into " & sFileNameNoExt & ": " & ex.Message & "]" & vbCrLf)
                Catch
                End Try
            End Try
        End If

    Next

End Sub


' ---------------------------------------------------------------------
' MODE 3 - CONSOLIDATE ONLY. A deliberately different, SAFER algorithm
' than Modes 1/2's ProcessLevel, built specifically to avoid the failure
' mode discovered in testing: ProcessLevel works bottom-up (recurse into
' a sub-assembly's children FIRST, decide whether to relocate/rename
' itself AFTER) - which means a shared sub-assembly's own in-memory
' occurrence table gets modified as a side effect of exploring it, even
' when that sub-assembly is never itself the target of a copy this run.
' If that same file is also referenced by a DIFFERENT, untouched
' assembly (e.g. because "the copy" only duplicated the TOP-level file,
' not its whole reference tree), that dirty in-memory state can end up
' silently saved back to the original file later, corrupting an assembly
' this rule was never even run on.
'
' ConsolidateLevel avoids this by working TOP-DOWN instead: the INSTANT
' a match is found that isn't already sitting in this assembly's folder,
' an independent copy is made FIRST (SaveAs, SaveCopyAs=True - the
' original stays bound to its own file and is never written to), and
' ONLY THEN does recursion continue - into the NEW COPY, never the
' original. The original document's own occurrence table is therefore
' never mutated by this rule at all; it's read from (to make the copy)
' and left exactly as it was.
'
' No renaming happens here - sFind is only used as a STARTS WITH filter
' (same matching as Mode 1) to decide what qualifies; the file name
' itself never changes, only its location does.
'
' Derived source chains and linked parameter tables are also consolidated
' for every part encountered (ported from Traverse_Through_Subs_Parts_
' Update_Derived_Part.iLogicVb, adapted for location-only rather than
' name-swap logic) - a part whose only route to a foreign-folder file is
' via a Derived Component reference or a linked parameter table will
' have that source copied into the target folder and repointed.
Sub ConsolidateLevel(oCompDef As ComponentDefinition, sFind As String, sTargetFolder As String, sTopAssemblyFullName As String, oLog As System.Text.StringBuilder, ByRef iCount As Integer, ByRef oRenameMap As System.Collections.Generic.Dictionary(Of String, String), ByRef oVisitedLevels As System.Collections.Generic.HashSet(Of String), ByRef oPathStack As System.Collections.Generic.List(Of String), sLogFilePath As String, ByRef oProcessedDerivedDocs As System.Collections.Generic.HashSet(Of String))

    Dim sThisLevelFullName As String = oCompDef.Document.FullFileName

    ' CYCLE GUARD: only block if this file is literally our own ancestor in
    ' the current path stack - a true circular reference. oVisitedLevels
    ' mirrors oPathStack for O(1) lookup. This is NOT the same as "have we
    ' ever visited this file" - a shared sub-assembly legitimately placed in
    ' multiple parents must be reachable from each of those parents, so we
    ' must NOT gate on a global "already seen" check here. The oRenameMap
    ' already tracks which files have been consolidated this run - that is
    ' the correct dedup for "don't re-copy the same file twice", which is
    ' handled at the occurrence level below, not at this entry-point level.
    If oVisitedLevels.Contains(sThisLevelFullName) Then
        oLog.Append(vbCrLf & "CYCLE GUARD: '" & sThisLevelFullName & "' is its own ancestor on this path (" & String.Join(" > ", oPathStack) & ") - skipping.")
        Exit Sub
    End If
    oVisitedLevels.Add(sThisLevelFullName)
    oPathStack.Add(sThisLevelFullName)

    Try
        Try
            System.IO.File.AppendAllText(sLogFilePath, DateTime.Now.ToString("HH:mm:ss.fff") & "  CONSOLIDATE ENTERING: " & sThisLevelFullName & vbCrLf)
        Catch
        End Try

        ' Snapshot occurrences before iterating - Replace() below can
        ' otherwise disturb a live enumerator mid-loop.
        Dim oOccList As New System.Collections.Generic.List(Of ComponentOccurrence)
        For Each oOcc As ComponentOccurrence In oCompDef.Occurrences
            oOccList.Add(oOcc)
        Next

        ' TWO-PASS APPROACH: eliminates concurrent SaveAs collisions.
        '
        ' The original single-pass approach would start SaveAs on assembly A,
        ' then immediately start SaveAs on sibling assembly B (from the next
        ' iteration) before A's SaveAs had finished writing to disk. Inventor's
        ' SaveAs is not safe to call concurrently on multiple assemblies in the
        ' same session - the second call can interrupt the first, leaving the
        ' first file partially written or not written at all.
        '
        ' PASS 1: walk every occurrence at THIS level. For anything that needs
        ' copying, do the SaveAs and repoint NOW - fully, one at a time, in
        ' sequence. Do NOT recurse into children yet. Record which new copies
        ' need child-recursion in oNeedsRecurse.
        '
        ' PASS 2: once all siblings at this level are safely copied and
        ' repointed, THEN recurse into each new copy's children. By this
        ' point every sibling's file is confirmed on disk, so no concurrent
        ' SaveAs can occur at this level.

        Dim oNeedsRecurse As New System.Collections.Generic.List(Of System.Tuple(Of String, Document))  ' (new file path, new doc)

        ' UNSUPPRESS CYCLE: record which occurrences are currently suppressed,
        ' unsuppress them all before the loop, then re-suppress them in a
        ' Finally block after. This lets the normal active-occurrence path
        ' handle them fully (SaveAs, Replace, child recursion) without any
        ' special-case suppressed code inside the loop. The assembly is always
        ' left in its original suppression state regardless of what happens.
        Dim oSuppressedOccs As New System.Collections.Generic.List(Of ComponentOccurrence)
        For Each oOcc As ComponentOccurrence In oOccList
            Try
                If oOcc.Suppressed Then oSuppressedOccs.Add(oOcc)
            Catch
            End Try
        Next

        If oSuppressedOccs.Count > 0 Then
            Try
                System.IO.File.AppendAllText(sLogFilePath, "      " & DateTime.Now.ToString("HH:mm:ss.fff") & "  Unsuppressing " & oSuppressedOccs.Count & " occurrence(s) for consolidation pass." & vbCrLf)
            Catch
            End Try
            For Each oSuppOcc As ComponentOccurrence In oSuppressedOccs
                Try
                    oSuppOcc.Unsuppress()
                Catch exUnsupp As Exception
                    Try
                        System.IO.File.AppendAllText(sLogFilePath, "      " & DateTime.Now.ToString("HH:mm:ss.fff") & "  WARNING: could not unsuppress " & oSuppOcc.Name & ": " & exUnsupp.Message & vbCrLf)
                    Catch
                    End Try
                End Try
            Next
            ' Re-snapshot the occurrence list now that suppressed ones are active.
            oOccList = New System.Collections.Generic.List(Of ComponentOccurrence)
            For Each oOcc As ComponentOccurrence In oCompDef.Occurrences
                oOccList.Add(oOcc)
            Next
        End If

        Try ' Unsuppress/re-suppress guard - Finally always re-suppresses

        For Each oOcc As ComponentOccurrence In oOccList

            ' All occurrences are now active - the re-suppress Finally below
            ' restores original suppression state after the loop.

            Dim oRefDoc As Document = Nothing
            Dim sFull As String = ""
            Try
                oRefDoc = oOcc.Definition.Document
                sFull = oRefDoc.FullFileName
            Catch
                ' Definition.Document failed even for an active occurrence.
                ' Try ReferencedFileDescriptor as a last resort.
                Dim sFallbackPath As String = ""
                Try
                    sFallbackPath = oOcc.ReferencedFileDescriptor.FullFileName
                Catch
                    sFallbackPath = ""
                End Try

                If sFallbackPath <> "" AndAlso Not sFallbackPath.Contains("*") AndAlso System.IO.File.Exists(sFallbackPath) Then
                    Dim sFbExt As String = System.IO.Path.GetExtension(sFallbackPath).ToUpper()
                    Dim sFbName As String = System.IO.Path.GetFileName(sFallbackPath)
                    If (sFbExt = ".IPT" OrElse sFbExt = ".IAM") AndAlso
                       Not IsInExcludedFolder(sFallbackPath) AndAlso
                       System.IO.Path.GetFileNameWithoutExtension(sFallbackPath).ToUpper().StartsWith(sFind.ToUpper()) Then
                        Dim sFbTarget As String = System.IO.Path.Combine(sTargetFolder, sFbName)
                        If Not System.IO.File.Exists(sFbTarget) Then
                            Try
                                System.IO.File.Copy(sFallbackPath, sFbTarget, False)
                                oLog.Append(vbCrLf & "UNLOADED (copied via ReferencedFileDescriptor - definition not accessible): " & sFbName)
                                iCount = iCount + 1
                            Catch exFb As Exception
                                oLog.Append(vbCrLf & "UNLOADED (File.Copy failed): " & sFbName & " (" & exFb.Message & ")")
                            End Try
                        Else
                            oLog.Append(vbCrLf & "UNLOADED (copy already exists): " & sFbName)
                        End If
                    End If
                End If
                Continue For
            End Try

            If Trim(sFull) = "" Then Continue For ' virtual component
            If sFull.Contains("*") Then Continue For ' virtual/private pseudo-path
            If IsSyntheticPatternMemberName(sFull) Then Continue For
            If String.Compare(sFull, sThisLevelFullName, True) = 0 Then Continue For ' virtual component sharing parent's identity

            If IsInExcludedFolder(sFull) Then Continue For
            If IsContentCenterMember(oRefDoc) Then Continue For

            ' --- Already consolidated elsewhere this run (shared reference)? ---
            ' Repoint this occurrence to the known new location if needed.
            ' CRITICAL: do NOT skip recursing into children here just because
            ' the file is known. A shared sub-assembly (e.g. placed in both
            ' Support_Frame AND in the top-level V01-01-10 assembly) needs its
            ' own children consolidated regardless of which parent we first
            ' encountered it under. We use oProcessedDerivedDocs as a
            ' "children already fully processed" gate - that set is only added
            ' to AFTER children have been walked, not before.
            If oRenameMap.ContainsKey(sFull) Then
                Dim sKnownNewName As String = oRenameMap(sFull)

                ' If the mapped target is a different file, verify it actually
                ' exists on disk before repointing. If SaveAs failed (E_FAIL,
                ' file locked etc.) the map entry was still written but the
                ' file never landed - repointing to a non-existent file would
                ' corrupt the occurrence reference in the original. Skip both
                ' the repoint and the child recursion in this case; a re-run
                ' after a clean session will pick it up properly.
                If String.Compare(sKnownNewName, sFull, True) <> 0 AndAlso Not System.IO.File.Exists(sKnownNewName) Then
                    oLog.Append(vbCrLf & "SKIPPED repoint (target not on disk - SaveAs likely failed earlier): " & System.IO.Path.GetFileName(sFull) & "  -->  " & sKnownNewName)
                    Continue For
                End If

                If String.Compare(sKnownNewName, sFull, True) <> 0 Then
                    Try
                        oOcc.Replace(sKnownNewName, False)
                        iCount = iCount + 1
                        oLog.Append(vbCrLf & "Repointed (already consolidated this run): " & System.IO.Path.GetFileName(sFull) & "  -->  " & sKnownNewName)
                    Catch ex As Exception
                        oLog.Append(vbCrLf & "FAILED to repoint to already-consolidated file: " & ex.Message)
                    End Try
                End If
                ' If this is an assembly whose children haven't been processed
                ' yet from this effective target location, still recurse in.
                ' The cycle guard in ConsolidateLevel will handle any genuine
                ' circular references; this is just a shared component.
                If oRefDoc.DocumentType = kAssemblyDocumentObject Then
                    Dim sEffectiveNew As String = sKnownNewName
                    If Not oProcessedDerivedDocs.Contains(sEffectiveNew.ToUpper()) Then
                        oProcessedDerivedDocs.Add(sEffectiveNew.ToUpper())
                        Try
                            Dim oNewDoc As Document = Nothing
                            Try
                                oNewDoc = ThisApplication.Documents.ItemByName(sEffectiveNew)
                            Catch
                                oNewDoc = Nothing
                            End Try
                            Dim bNewDocQueuedHere As Boolean = False
                            If oNewDoc Is Nothing AndAlso System.IO.File.Exists(sEffectiveNew) Then oNewDoc = OpenDocTracked(sEffectiveNew, bNewDocQueuedHere)
                            ' Queue for Pass 2 - don't recurse mid-Pass-1
                            If oNewDoc IsNot Nothing Then oNeedsRecurse.Add(System.Tuple.Create(sEffectiveNew, oNewDoc))
                        Catch ex As Exception
                            oLog.Append(vbCrLf & "FAILED queuing shared consolidated assembly for Pass 2: " & System.IO.Path.GetFileName(sEffectiveNew) & " (" & ex.Message & ")")
                        End Try
                    End If
                End If
                Continue For
            End If

            Dim sFileNameNoExt As String = System.IO.Path.GetFileNameWithoutExtension(sFull)
            If Not sFileNameNoExt.ToUpper().StartsWith(sFind.ToUpper()) Then
                ' Doesn't match the project prefix - not something Mode 3
                ' touches. Still explore it directly (no copy needed, since
                ' we're not relocating THIS file) in case something matching
                ' is nested further down.
                If oRefDoc.DocumentType = kAssemblyDocumentObject Then
                    ' Queue for Pass 2 - explore children after all siblings copied
                    oNeedsRecurse.Add(System.Tuple.Create(sFull, oRefDoc))
                End If
                Continue For
            End If

            Dim sEffectiveTargetFolder As String = GetEffectiveTargetFolder(sFull, sTargetFolder)
            Dim sCurrentFolder As String = System.IO.Path.GetDirectoryName(sFull)

            If String.Compare(sCurrentFolder, sEffectiveTargetFolder, True) = 0 Then
                ' Already exactly where it should be - record it.
                oRenameMap(sFull) = sFull
                If oRefDoc.DocumentType = kAssemblyDocumentObject Then
                    If Not oProcessedDerivedDocs.Contains(sFull.ToUpper()) Then
                        oProcessedDerivedDocs.Add(sFull.ToUpper())
                        ' Queue for Pass 2 - don't recurse mid-Pass-1
                        oNeedsRecurse.Add(System.Tuple.Create(sFull, oRefDoc))
                    End If
                ElseIf oRefDoc.DocumentType = kPartDocumentObject Then
                    ' Part already in the right folder - still chase its derived
                    ' chain and param tables since something deeper may not be.
                    Dim bPartChanged As Boolean = False
                    Try
                        If ConsolidateDerivedChain(oRefDoc, sTargetFolder, oLog, iCount, oRenameMap, oProcessedDerivedDocs) Then bPartChanged = True
                    Catch ex As Exception
                        oLog.Append(vbCrLf & "FAILED consolidating derived chain in (already local): " & System.IO.Path.GetFileName(sFull) & " (" & ex.Message & ")")
                    End Try
                    Try
                        If ConsolidateLinkedParams(oRefDoc, sTargetFolder, oLog, iCount) Then bPartChanged = True
                    Catch ex As Exception
                        oLog.Append(vbCrLf & "FAILED consolidating param links in (already local): " & System.IO.Path.GetFileName(sFull) & " (" & ex.Message & ")")
                    End Try
                    If bPartChanged Then
                        Try
                            oRefDoc.Save2(False)
                        Catch ex As Exception
                            oLog.Append(vbCrLf & "FAILED to save after derived/param consolidation: " & System.IO.Path.GetFileName(sFull) & " (" & ex.Message & ")")
                        End Try
                    End If
                End If
                Continue For
            End If

            ' --- NEEDS RELOCATING: copy FIRST, before ever recursing into it. ---
            Dim sExt As String = System.IO.Path.GetExtension(sFull)
            Dim sNewFullName As String = System.IO.Path.Combine(sEffectiveTargetFolder, sFileNameNoExt & sExt)
            Dim bRoutedToNonStd As Boolean = (String.Compare(sEffectiveTargetFolder, sTargetFolder, True) <> 0)

            If String.Compare(sNewFullName, sTopAssemblyFullName, True) = 0 Then
                oLog.Append(vbCrLf & "SAFETY SKIP: '" & sFileNameNoExt & sExt & "' would collide with the TOP ASSEMBLY'S OWN FILE - refusing to consolidate. Left unchanged - check this one manually.")
                Continue For
            End If

            If System.IO.File.Exists(sNewFullName) Then
                ' A copy already exists at the target - repoint to it, then
                ' still make sure ITS OWN children get consolidated too (it
                ' may have been created by an earlier, incomplete run).
                '
                ' Before calling Replace, clear the read-only attribute on
                ' the PARENT assembly (the one whose occurrence list we are
                ' modifying - oRefDoc's parent, i.e. the assembly currently
                ' being processed at this ConsolidateLevel call). If that
                ' parent was itself created by File.Copy fallback, Vault has
                ' no record of it and treats it as read-only, causing
                ' oOcc.Replace() to throw E_FAIL. Clearing the attribute
                ' directly bypasses that interception.
                Try
                    Dim sParentPath As String = oCompDef.Document.FullFileName
                    Dim oAttrs As System.IO.FileAttributes = System.IO.File.GetAttributes(sParentPath)
                    If (oAttrs And System.IO.FileAttributes.ReadOnly) = System.IO.FileAttributes.ReadOnly Then
                        System.IO.File.SetAttributes(sParentPath, oAttrs And Not System.IO.FileAttributes.ReadOnly)
                    End If
                Catch
                    ' If we can't clear it, proceed anyway - Replace may still
                    ' work if Vault's interception is the only lock.
                End Try

                Try
                    oOcc.Replace(sNewFullName, False)
                    ' Rename browser node to match new filename.
                    Try
                        oOcc.Name = System.IO.Path.GetFileNameWithoutExtension(sNewFullName)
                    Catch
                    End Try
                    oRenameMap(sFull) = sNewFullName
                    iCount = iCount + 1
                    oLog.Append(vbCrLf & "CONSOLIDATED (already existed" & IIf(bRoutedToNonStd, ", routed to Non Std Parts", "") & "): " & sFileNameNoExt & sExt & "  -  repointed only, not re-copied")
                Catch ex As Exception
                    oLog.Append(vbCrLf & "FAILED to repoint to existing consolidated copy: " & sFileNameNoExt & sExt & " (" & ex.Message & ")")
                    Continue For
                End Try

                If sExt.ToUpper() = ".IAM" Then
                    Try
                        Dim oExistingCopyDoc As Document = Nothing
                        Try
                            oExistingCopyDoc = ThisApplication.Documents.ItemByName(sNewFullName)
                        Catch
                            oExistingCopyDoc = Nothing
                        End Try
                        Dim bExCopyDocQueuedHere As Boolean = False
                        If oExistingCopyDoc Is Nothing Then oExistingCopyDoc = OpenDocTracked(sNewFullName, bExCopyDocQueuedHere)
                        ' Queue for Pass 2 - don't recurse here mid-Pass-1
                        If oExistingCopyDoc IsNot Nothing Then oNeedsRecurse.Add(System.Tuple.Create(sNewFullName, oExistingCopyDoc))
                    Catch ex As Exception
                        oLog.Append(vbCrLf & "FAILED opening existing copy for later recursion: " & sFileNameNoExt & sExt & " (" & ex.Message & ")")
                    End Try
                ElseIf sExt.ToUpper() = ".IPT" Then
                    Dim bExPartChanged As Boolean = False
                    Try
                        Dim oExPartDoc As Document = Nothing
                        Dim bExPartOpenedHere As Boolean = False
                        Try
                            oExPartDoc = ThisApplication.Documents.ItemByName(sNewFullName)
                        Catch
                            oExPartDoc = Nothing
                        End Try
                        If oExPartDoc Is Nothing Then oExPartDoc = OpenDocTracked(sNewFullName, bExPartOpenedHere)
                        If ConsolidateDerivedChain(oExPartDoc, sTargetFolder, oLog, iCount, oRenameMap, oProcessedDerivedDocs) Then bExPartChanged = True
                        If ConsolidateLinkedParams(oExPartDoc, sTargetFolder, oLog, iCount) Then bExPartChanged = True
                        If bExPartChanged Then oExPartDoc.Save2(False)
                        CloseIfOpenedHere(oExPartDoc, bExPartOpenedHere)
                    Catch ex As Exception
                        oLog.Append(vbCrLf & "FAILED consolidating derived/params in existing part copy: " & sFileNameNoExt & sExt & " (" & ex.Message & ")")
                    End Try
                End If

            Else
                ' Create the copy. The ORIGINAL document (oRefDoc) is only
                ' ever read from here - SaveCopyAs=True leaves it bound to
                ' its own original file, completely untouched.
                ' Each sub-operation below has its own Try/Catch so failures
                ' are handled individually and execution always falls through
                ' to the next step rather than being swallowed by one big
                ' outer Catch.

                ' Pre-check: if the target file already exists AND is
                ' currently open in this Inventor session, SaveAs will
                ' fail with E_FAIL (0x80004005 - file locked). Treat this
                ' the same as the "already existed" branch above - repoint
                ' to the existing copy and recurse into its children.
                If System.IO.File.Exists(sNewFullName) Then
                    Dim oAlreadyOpen As Document = Nothing
                    Try
                        oAlreadyOpen = ThisApplication.Documents.ItemByName(sNewFullName)
                    Catch
                        oAlreadyOpen = Nothing
                    End Try

                    If oAlreadyOpen IsNot Nothing Then
                        ' File exists and is open - treat as already-consolidated.
                        Try
                            oOcc.Replace(sNewFullName, False)
                            oRenameMap(sFull) = sNewFullName
                            iCount = iCount + 1
                            oLog.Append(vbCrLf & "CONSOLIDATED (already existed + open in session, repointed): " & sFileNameNoExt & sExt)
                        Catch ex As Exception
                            oLog.Append(vbCrLf & "FAILED to repoint to open existing copy: " & sFileNameNoExt & sExt & " (" & ex.Message & ")")
                        End Try

                        If sExt.ToUpper() = ".IAM" AndAlso Not oProcessedDerivedDocs.Contains(sNewFullName.ToUpper()) Then
                            oProcessedDerivedDocs.Add(sNewFullName.ToUpper())
                            ' Queue for Pass 2
                            oNeedsRecurse.Add(System.Tuple.Create(sNewFullName, CType(oAlreadyOpen, Document)))
                        End If
                        Continue For
                    End If
                End If

                Try
                    System.IO.File.AppendAllText(sLogFilePath, "      " & DateTime.Now.ToString("HH:mm:ss.fff") & "  Consolidate SaveAs starting: " & sFileNameNoExt & sExt & vbCrLf)
                Catch
                End Try

                ' SAVE STRATEGY: try SaveAs first. If it throws (E_FAIL from
                ' Vault interception on a checked-in file) OR silently returns
                ' without writing (the other Vault interception variant), fall
                ' back to a plain OS File.Copy. File.Copy bypasses Vault's
                ' add-in interception entirely since it operates at the Windows
                ' file system level. The copy still contains the original
                ' references (pointing at the source folder) which is exactly
                ' what we want - ConsolidateLevel opens it and fixes its
                ' internal references in Pass 2.
                '
                ' bSaveAsOk tracks whether SaveAs completed without throwing.
                ' File.Copy is only attempted when bSaveAsOk is False (threw)
                ' OR the file still isn't on disk after the poll (silent
                ' intercept). This prevents the double-copy seen in earlier
                ' runs where "SaveAs finished" and "File.Copy fallback succeeded"
                ' both appeared for the same file - SaveAs had completed fine
                ' but the 5-second poll timed out before the file flushed, so
                ' File.Copy ran unnecessarily on an already-written file.
                Dim bSaveAsOk As Boolean = False
                Try
                    oRefDoc.SaveAs(sNewFullName, True)

                    ' Inventor's SaveAs on an assembly can return before the
                    ' file is fully flushed to disk. Poll briefly to confirm
                    ' the file landed - up to 5 seconds.
                    Dim iWaitMs As Integer = 0
                    Do While Not System.IO.File.Exists(sNewFullName) AndAlso iWaitMs < 5000
                        System.Threading.Thread.Sleep(100)
                        iWaitMs = iWaitMs + 100
                    Loop

                    bSaveAsOk = True
                    Try
                        System.IO.File.AppendAllText(sLogFilePath, "      " & DateTime.Now.ToString("HH:mm:ss.fff") & "  Consolidate SaveAs finished." & vbCrLf)
                    Catch
                    End Try
                Catch exSaveAs As Exception
                    ' SaveAs threw (E_FAIL or similar) - log it and fall
                    ' through to the File.Copy fallback below.
                    Try
                        System.IO.File.AppendAllText(sLogFilePath, "      " & DateTime.Now.ToString("HH:mm:ss.fff") & "  SaveAs threw (" & exSaveAs.Message & ") - will attempt File.Copy fallback." & vbCrLf)
                    Catch
                    End Try
                End Try

                ' Only attempt File.Copy if SaveAs threw (bSaveAsOk=False) OR
                ' the file still isn't on disk after the poll (silent Vault
                ' intercept). If SaveAs completed without throwing and the file
                ' is present, the fallback is skipped entirely - this is the
                ' fix for the double-copy issue.
                If Not bSaveAsOk OrElse Not System.IO.File.Exists(sNewFullName) Then
                    Try
                        System.IO.File.Copy(sFull, sNewFullName, False)
                        Try
                            System.IO.File.AppendAllText(sLogFilePath, "      " & DateTime.Now.ToString("HH:mm:ss.fff") & "  File.Copy fallback succeeded (SaveAs threw or produced no file)." & vbCrLf)
                        Catch
                        End Try
                    Catch exCopy As Exception
                        oLog.Append(vbCrLf & "FAILED to consolidate: " & sFileNameNoExt & sExt & " (SaveAs threw E_FAIL, File.Copy fallback also failed: " & exCopy.Message & ")")
                        Try
                            System.IO.File.AppendAllText(sLogFilePath, "      " & DateTime.Now.ToString("HH:mm:ss.fff") & "  File.Copy fallback FAILED: " & exCopy.Message & vbCrLf)
                        Catch
                        End Try
                        Continue For
                    End Try
                End If

                ' Final verify: if neither SaveAs nor File.Copy produced the
                ' file, skip rather than repoint to a non-existent path.
                If Not System.IO.File.Exists(sNewFullName) Then
                    oLog.Append(vbCrLf & "FAILED to consolidate (file not on disk after SaveAs + File.Copy): " & sFileNameNoExt & sExt)
                    Try
                        System.IO.File.AppendAllText(sLogFilePath, "      " & DateTime.Now.ToString("HH:mm:ss.fff") & "  Consolidate - FILE NOT FOUND after both SaveAs and File.Copy (skipped)." & vbCrLf)
                    Catch
                    End Try
                    Continue For
                End If

                Try
                    oOcc.Replace(sNewFullName, False)
                    ' Rename browser node to match new filename.
                    Try
                        oOcc.Name = System.IO.Path.GetFileNameWithoutExtension(sNewFullName)
                    Catch
                    End Try
                    oRenameMap(sFull) = sNewFullName
                    iCount = iCount + 1
                    oLog.Append(vbCrLf & "CONSOLIDATED (copied from " & sCurrentFolder & IIf(bRoutedToNonStd, ", routed to Non Std Parts", "") & "): " & sFileNameNoExt & sExt)
                Catch ex As Exception
                    oLog.Append(vbCrLf & "FAILED to repoint after copy: " & sFileNameNoExt & sExt & " (" & ex.Message & ")")
                    Continue For
                End Try

                ' PASS 1: record the new copy for child recursion in Pass 2.
                ' Do NOT recurse here - all siblings must be fully copied first
                ' to prevent concurrent SaveAs collisions.
                If sExt.ToUpper() = ".IAM" Then
                    Try
                        Dim bCopyOpened As Boolean = False
                        Dim oNewCopyDoc As Document = OpenDocTracked(sNewFullName, bCopyOpened)
                        If oNewCopyDoc IsNot Nothing Then
                            oNeedsRecurse.Add(System.Tuple.Create(sNewFullName, oNewCopyDoc))
                            ' Keep open for Pass 2 recursion; final cleanup closes if we opened it
                        End If
                    Catch ex As Exception
                        oLog.Append(vbCrLf & "FAILED opening new copy for later recursion: " & sFileNameNoExt & sExt & " (" & ex.Message & ")")
                    End Try
                ElseIf sExt.ToUpper() = ".IPT" Then
                    ' Parts: do derived/param consolidation now (no child
                    ' assembly recursion needed so no concurrent SaveAs risk).
                    Dim bNewPartChanged As Boolean = False
                    Try
                        Dim bPartOpenedHere As Boolean = False
                        Dim oNewPartDoc As Document = OpenDocTracked(sNewFullName, bPartOpenedHere)
                        If oNewPartDoc IsNot Nothing Then
                            If ConsolidateDerivedChain(oNewPartDoc, sTargetFolder, oLog, iCount, oRenameMap, oProcessedDerivedDocs) Then bNewPartChanged = True
                            If ConsolidateLinkedParams(oNewPartDoc, sTargetFolder, oLog, iCount) Then bNewPartChanged = True
                            If bNewPartChanged Then oNewPartDoc.Save2(False)
                            CloseIfOpenedHere(oNewPartDoc, bPartOpenedHere)
                            oNewPartDoc = Nothing
                        End If
                    Catch ex As Exception
                        oLog.Append(vbCrLf & "FAILED consolidating derived/params in new part copy: " & sFileNameNoExt & sExt & " (" & ex.Message & ")")
                    End Try
                End If
            End If

        Next ' end Pass 1

        Catch ex As Exception
            ' Unexpected exception from Pass 1 - log it but still fall through
            ' to Finally so re-suppress always runs.
            oLog.Append(vbCrLf & "UNEXPECTED ERROR in Pass 1 consolidation loop: " & ex.Message)
        Finally
            ' RE-SUPPRESS: restore any occurrences that were suppressed before
            ' this ConsolidateLevel call. Runs unconditionally so the assembly
            ' is always left in its original suppression state.
            If oSuppressedOccs.Count > 0 Then
                Try
                    System.IO.File.AppendAllText(sLogFilePath, "      " & DateTime.Now.ToString("HH:mm:ss.fff") & "  Re-suppressing " & oSuppressedOccs.Count & " occurrence(s)." & vbCrLf)
                Catch
                End Try
                For Each oSuppOcc As ComponentOccurrence In oSuppressedOccs
                    Try
                        oSuppOcc.Suppress()
                    Catch exResupp As Exception
                        Try
                            System.IO.File.AppendAllText(sLogFilePath, "      " & DateTime.Now.ToString("HH:mm:ss.fff") & "  WARNING: could not re-suppress " & oSuppOcc.Name & ": " & exResupp.Message & vbCrLf)
                        Catch
                        End Try
                    End Try
                Next
            End If
        End Try ' end unsuppress/re-suppress guard

        ' PASS 2: now that all siblings at this level are safely copied and
        ' confirmed on disk, recurse into each new assembly copy's children.
        For Each oTuple As System.Tuple(Of String, Document) In oNeedsRecurse
            Try
                Dim oNewCopyDoc As Document = oTuple.Item2
                ConsolidateLevel(oNewCopyDoc.ComponentDefinition, sFind, sTargetFolder, sTopAssemblyFullName, oLog, iCount, oRenameMap, oVisitedLevels, oPathStack, sLogFilePath, oProcessedDerivedDocs)
                If oNewCopyDoc.Dirty Then oNewCopyDoc.Save2(False)
            Catch ex As Exception
                oLog.Append(vbCrLf & "FAILED consolidating children in Pass 2: " & System.IO.Path.GetFileName(oTuple.Item1) & " (" & ex.Message & ")")
            End Try
        Next

    Finally
        oVisitedLevels.Remove(sThisLevelFullName)
        oPathStack.RemoveAt(oPathStack.Count - 1)
    End Try

End Sub


' ---------------------------------------------------------------------
' CONSOLIDATE DERIVED CHAIN (Mode 3 companion)
' Ported from Traverse_Through_Subs_Parts_Update_Derived_Part.iLogicVb
' and adapted for location-only consolidation (no name swapping).
'
' For each file in oPartDoc's ReferencedFileDescriptors: if the source
' sits outside sTargetFolder, copies it there (same name) FIRST, then
' recurses into THAT source's own derived chain - same bottom-up
' principle as the original derived rule, just checking folder location
' rather than old-name -> new-name matching. Returns True if anything
' in oPartDoc's own reference table changed (so the caller saves it).
' ---------------------------------------------------------------------
Function ConsolidateDerivedChain(oPartDoc As Document, sTargetFolder As String, oLog As System.Text.StringBuilder, ByRef iCount As Integer, ByRef oRenameMap As System.Collections.Generic.Dictionary(Of String, String), ByRef oProcessedDerivedDocs As System.Collections.Generic.HashSet(Of String)) As Boolean

    Dim bChanged As Boolean = False

    For Each oFileDesc As FileDescriptor In oPartDoc.File.ReferencedFileDescriptors

        Dim sRefFullName As String = ""
        Try
            sRefFullName = oFileDesc.FullFileName
        Catch
            Continue For
        End Try

        If Trim(sRefFullName) = "" Then Continue For
        If IsInExcludedFolder(sRefFullName) Then Continue For

        ' Only process Inventor native files. Any other referenced file type
        ' (.dwg, .stp, .step, .stl, .obj, .xlsx, .xls, mesh files etc.) is
        ' skipped - opening these via Documents.Open would hand them off to
        ' AutoCAD or another application and stall the rule waiting for that
        ' window. Their references can't be repointed through the Inventor
        ' API anyway so skipping is correct, not just a workaround.
        Dim sRefExtCheck As String = System.IO.Path.GetExtension(sRefFullName).ToUpper()
        If sRefExtCheck <> ".IPT" AndAlso sRefExtCheck <> ".IAM" Then
            oLog.Append(vbCrLf & "  DERIVED: skipped non-Inventor file (" & sRefExtCheck & "): " & System.IO.Path.GetFileName(sRefFullName))
            Continue For
        End If

        ' Already resolved this run - just repoint.
        If oRenameMap.ContainsKey(sRefFullName) Then
            Dim sKnownNew As String = oRenameMap(sRefFullName)
            If String.Compare(sKnownNew, sRefFullName, True) <> 0 Then
                Try
                    oFileDesc.ReplaceReference(sKnownNew)
                    iCount = iCount + 1
                    oLog.Append(vbCrLf & "  DERIVED repointed (already consolidated): " & System.IO.Path.GetFileName(sRefFullName) & "  -->  " & System.IO.Path.GetFileName(sKnownNew))
                    bChanged = True
                Catch ex As Exception
                    oLog.Append(vbCrLf & "  DERIVED repoint FAILED (already consolidated): " & System.IO.Path.GetFileName(sRefFullName) & " (" & ex.Message & ")")
                End Try
            End If
            Continue For
        End If

        Dim sRefFolder As String = System.IO.Path.GetDirectoryName(sRefFullName)
        Dim sFileNameNoExt As String = System.IO.Path.GetFileNameWithoutExtension(sRefFullName)
        Dim sExt As String = System.IO.Path.GetExtension(sRefFullName)
        Dim sNewFullName As String = System.IO.Path.Combine(sTargetFolder, sFileNameNoExt & sExt)

        If String.Compare(sRefFolder, sTargetFolder, True) = 0 Then
            ' Already in target folder - record and recurse if a part.
            oRenameMap(sRefFullName) = sRefFullName
            If Not oProcessedDerivedDocs.Contains(sRefFullName) AndAlso sExt.ToUpper() = ".IPT" Then
                oProcessedDerivedDocs.Add(sRefFullName)
                Dim oSourceDoc As Document = Nothing
                Dim bSourceDocOpenedHere As Boolean = False
                Try
                    Try
                        oSourceDoc = ThisApplication.Documents.ItemByName(sRefFullName)
                    Catch
                        oSourceDoc = Nothing
                    End Try
                    If oSourceDoc Is Nothing Then oSourceDoc = OpenDocTracked(sRefFullName, bSourceDocOpenedHere)
                    If oSourceDoc Is Nothing Then Throw New Exception("could not open document")
                    If ConsolidateDerivedChain(oSourceDoc, sTargetFolder, oLog, iCount, oRenameMap, oProcessedDerivedDocs) Then
                        oSourceDoc.Save2(False)
                    End If
                Catch ex As Exception
                    oLog.Append(vbCrLf & "  DERIVED: failed recursing into (already local): " & System.IO.Path.GetFileName(sRefFullName) & " (" & ex.Message & ")")
                End Try
                CloseIfOpenedHere(oSourceDoc, bSourceDocOpenedHere)
            End If
            Continue For
        End If

        ' Needs copying into target folder.
        Dim oSourceDocToCopy As Document = Nothing
        Dim bSrcCopyOpenedHere As Boolean = False
        Try
            Try
                oSourceDocToCopy = ThisApplication.Documents.ItemByName(sRefFullName)
            Catch
                oSourceDocToCopy = Nothing
            End Try
            If oSourceDocToCopy Is Nothing Then oSourceDocToCopy = OpenDocTracked(sRefFullName, bSrcCopyOpenedHere)
            If oSourceDocToCopy Is Nothing Then Throw New Exception("could not open document")
        Catch ex As Exception
            oLog.Append(vbCrLf & "  DERIVED: failed to open source for copying: " & System.IO.Path.GetFileName(sRefFullName) & " (" & ex.Message & ")")
            Continue For
        End Try

        ' Recurse into source's own chain FIRST (bottom-up), so the copy
        ' carries no stale deeper links.
        If Not oProcessedDerivedDocs.Contains(sRefFullName) AndAlso sExt.ToUpper() = ".IPT" Then
            oProcessedDerivedDocs.Add(sRefFullName)
            Try
                ConsolidateDerivedChain(oSourceDocToCopy, sTargetFolder, oLog, iCount, oRenameMap, oProcessedDerivedDocs)
            Catch ex As Exception
                oLog.Append(vbCrLf & "  DERIVED: failed recursing into chain before copy: " & System.IO.Path.GetFileName(sRefFullName) & " (" & ex.Message & ")")
            End Try
        End If

        If System.IO.File.Exists(sNewFullName) Then
            ' Target already exists - repoint to it.
            Try
                oFileDesc.ReplaceReference(sNewFullName)
                oRenameMap(sRefFullName) = sNewFullName
                iCount = iCount + 1
                oLog.Append(vbCrLf & "  DERIVED consolidated (already existed): " & sFileNameNoExt & sExt)
                bChanged = True
            Catch ex As Exception
                oLog.Append(vbCrLf & "  DERIVED: failed to repoint to existing copy: " & sFileNameNoExt & sExt & " (" & ex.Message & ")")
            End Try
        Else
            Try
                oSourceDocToCopy.SaveAs(sNewFullName, True)
                oFileDesc.ReplaceReference(sNewFullName)
                oRenameMap(sRefFullName) = sNewFullName
                iCount = iCount + 1
                oLog.Append(vbCrLf & "  DERIVED consolidated (copied from " & sRefFolder & "): " & sFileNameNoExt & sExt)
                bChanged = True
            Catch ex As Exception
                oLog.Append(vbCrLf & "  DERIVED: failed to copy: " & sFileNameNoExt & sExt & " (" & ex.Message & ")")
            End Try
        End If

        ' Release the source if this function opened it (skips initially-open / dirty docs)
        CloseIfOpenedHere(oSourceDocToCopy, bSrcCopyOpenedHere)

    Next

    Return bChanged

End Function


' ---------------------------------------------------------------------
' CONSOLIDATE LINKED PARAM TABLES (Mode 3 companion)
' Ported from Traverse_Through_Subs_Parts_Update_Derived_Part.iLogicVb
' and adapted for location-only consolidation.
'
' For each linked parameter table on oDoc: if the referenced file sits
' outside sTargetFolder and a same-name copy exists there, repoints to
' it. If no copy exists yet, logs it as needing attention (param table
' files are not auto-copied here since they may be intentionally shared
' spreadsheets/iLogic files). Returns True if anything changed.
' ---------------------------------------------------------------------
Function ConsolidateLinkedParams(oDoc As Document, sTargetFolder As String, oLog As System.Text.StringBuilder, ByRef iCount As Integer) As Boolean

    Dim bChanged As Boolean = False
    ' Collect ALL parameter table collections to process.
    ' DerivedParameterTables: ipt/xlsx linked sources in parts and assemblies.
    ' ParameterSets: ASSEMBLY-level xlsx User Parameters - separate collection.
    Dim oTableCollections As New System.Collections.Generic.List(Of Object)
    Try
        Dim oDPT As Object = oDoc.ComponentDefinition.Parameters.DerivedParameterTables
        If oDPT IsNot Nothing AndAlso oDPT.Count > 0 Then oTableCollections.Add(oDPT)
    Catch
    End Try
    If oDoc.DocumentType = kAssemblyDocumentObject Then
        Try
            Dim oPS As Object = oDoc.ComponentDefinition.Parameters.ParameterSets
            If oPS IsNot Nothing AndAlso oPS.Count > 0 Then oTableCollections.Add(oPS)
        Catch
        End Try
    End If
    If oTableCollections.Count = 0 Then Return False

    Dim sDocName As String = System.IO.Path.GetFileName(oDoc.FullFileName)

    For Each oTables As Object In oTableCollections
        For i As Integer = oTables.Count To 1 Step -1
            Dim oTable As Object = oTables.Item(i)
            Dim sRefFullName As String = ""
            Try
                sRefFullName = oTable.ReferencedDocumentDescriptor.FullDocumentName
            Catch
                Continue For
            End Try

            Dim sRefFolder As String = System.IO.Path.GetDirectoryName(sRefFullName)
            If String.Compare(sRefFolder, sTargetFolder, True) = 0 Then Continue For ' already in the right place

            If IsInExcludedFolder(sRefFullName) Then Continue For

            Dim sRefFileName As String = System.IO.Path.GetFileNameWithoutExtension(sRefFullName)
            Dim sExt As String = System.IO.Path.GetExtension(sRefFullName)

            ' Skip non-Inventor param table sources (e.g. .xlsx, .dwg) - opening
            ' them would trigger AutoCAD or Excel and stall the rule. These are
            ' typically intentionally shared files; flag them for manual review.
            If sExt.ToUpper() <> ".IPT" AndAlso sExt.ToUpper() <> ".IAM" AndAlso sExt.ToUpper() <> ".XLS" AndAlso sExt.ToUpper() <> ".XLSX" Then
                oLog.Append(vbCrLf & "  PARAM TABLE: skipped non-standard file type (" & sExt & ") in " & sDocName & ": " & sRefFileName & sExt)
                Continue For
            End If
            Dim sNewFullName As String = System.IO.Path.Combine(sTargetFolder, sRefFileName & sExt)

            If Not System.IO.File.Exists(sNewFullName) Then
                oLog.Append(vbCrLf & "  PARAM TABLE not found in target folder (not copied - may be a shared spreadsheet): " & sDocName & " -> " & sRefFileName & sExt)
                Continue For
            End If

            Dim bDone As Boolean = False
            Try
                oTable.ReferencedDocumentDescriptor.ReferencedFileDescriptor.ReplaceReference(sNewFullName)
                If String.Compare(System.IO.Path.GetFileName(oTable.ReferencedDocumentDescriptor.FullDocumentName), sRefFileName & sExt, True) = 0 Then
                    bDone = True
                End If
            Catch
            End Try

            If Not bDone Then
                Try
                    oTable.Delete()
                    oTables.Add(sNewFullName)
                    bDone = True
                Catch ex As Exception
                    oLog.Append(vbCrLf & "  PARAM TABLE relink FAILED in " & sDocName & ": " & sRefFileName & sExt & " (" & ex.Message & ")")
                End Try
            End If

            If bDone Then
                iCount = iCount + 1
                bChanged = True
                oLog.Append(vbCrLf & "  PARAM TABLE consolidated in " & sDocName & ": " & sRefFileName & sExt)
            End If
        Next
    Next

    Return bChanged

End Function


' ---------------------------------------------------------------------
' FIX 3 - UPDATE LINKED PARAM TABLES AFTER RENAME (Mode 1/2 companion)
' Called from ProcessLevel on every part/assembly occurrence, mirroring
' the ProcessDerivedSource call. Walks the document's DerivedParameterTables
' and repoints any that reference a file tracked in oRenameMap (old path ->
' new path). This fixes the case where a Mode 1 rename has already created
' the new-named source (e.g. PJ00888-LC-006-000-000.ipt) but the PART that
' links to it as a parameter table still points at the old path
' (PJ00184-LC-006-000-000.ipt) because ConsolidateLinkedParams only handles
' same-name folder moves, not rename-and-move. Returns True if anything
' changed (so the caller knows to save the document).
' ---------------------------------------------------------------------
Function UpdateLinkedParamsAfterRename(oDoc As Document, ByRef oRenameMap As System.Collections.Generic.Dictionary(Of String, String), oLog As System.Text.StringBuilder, ByRef iCount As Integer, Optional sFind As String = "", Optional sReplace As String = "", Optional bUseContainsMode As Boolean = False, Optional sTargetFolder As String = "", Optional ByRef oNeedsCheckout As System.Collections.Generic.HashSet(Of String) = Nothing) As Boolean

    Dim bChanged As Boolean = False
    Dim oTables As Object = Nothing

    Try
        oTables = oDoc.ComponentDefinition.Parameters.DerivedParameterTables
    Catch
        Return False
    End Try

    If oTables Is Nothing OrElse oTables.Count = 0 Then Return False

    Dim sDocName As String = System.IO.Path.GetFileName(oDoc.FullFileName)

    For i As Integer = oTables.Count To 1 Step -1
        Dim oTable As Object = oTables.Item(i)
        Dim sRefFullName As String = ""
        Try
            sRefFullName = oTable.ReferencedDocumentDescriptor.FullDocumentName
        Catch
            Continue For
        End Try

        If Trim(sRefFullName) = "" Then Continue For

        ' Check rename map (case-insensitive) - is this source one we renamed?
        Dim sNewFullName As String = ""
        For Each kvp As System.Collections.Generic.KeyValuePair(Of String, String) In oRenameMap
            If String.Compare(kvp.Key, sRefFullName, True) = 0 Then
                sNewFullName = kvp.Value
                Exit For
            End If
        Next

        ' FIX B: if not in oRenameMap, also try Find/Replace pattern directly.
        ' oRenameMap is empty when the source was renamed in a PREVIOUS run.
        ' If the param source matches sFind AND a renamed copy exists in sTargetFolder,
        ' repoint to it now.
        If sNewFullName = "" AndAlso sFind <> "" AndAlso sTargetFolder <> "" Then
            Dim sFbRefName As String = System.IO.Path.GetFileNameWithoutExtension(sRefFullName)
            Dim sFbExt As String = System.IO.Path.GetExtension(sRefFullName)
            Dim bFbMatch As Boolean
            If bUseContainsMode Then
                bFbMatch = sFbRefName.ToUpper().Contains(sFind.ToUpper())
            Else
                bFbMatch = sFbRefName.ToUpper().StartsWith(sFind.ToUpper())
            End If
            If bFbMatch Then
                Dim sFbNewName As String
                If bUseContainsMode Then
                    sFbNewName = ReplaceAllCaseInsensitive(sFbRefName, sFind, sReplace)
                Else
                    sFbNewName = sReplace & sFbRefName.Substring(sFind.Length)
                End If
                Dim sFbNewFull As String = System.IO.Path.Combine(sTargetFolder, sFbNewName & sFbExt)
                If System.IO.File.Exists(sFbNewFull) Then
                    ' Renamed target exists - repoint to it.
                    sNewFullName = sFbNewFull
                ElseIf System.IO.File.Exists(sRefFullName) Then
                    ' Target copy doesn't exist yet but source does.
                    ' Copy it now - assembly-level xlsx in ParameterSets are
                    ' not handled by ProcessDerivedSource (which only runs on
                    ' parts). Frame Generator and other assemblies with
                    ' assembly-level parameter table links need the xlsx
                    ' copied here.
                    Try
                        If Not System.IO.Directory.Exists(System.IO.Path.GetDirectoryName(sFbNewFull)) Then
                            System.IO.Directory.CreateDirectory(System.IO.Path.GetDirectoryName(sFbNewFull))
                        End If
                        CopyXlsxSilently(sRefFullName, sFbNewFull)
                        If System.IO.File.Exists(sFbNewFull) Then
                            sNewFullName = sFbNewFull
                            oLog.Append(vbCrLf & "  PARAM TABLE (xlsx copied to target): " & sDocName & " -> " & sFbNewName & sFbExt)
                        End If
                    Catch exCopyXlsx As Exception
                        oLog.Append(vbCrLf & "  PARAM TABLE (xlsx copy FAILED): " & sDocName & " -> " & sFbNewName & sFbExt & " (" & exCopyXlsx.Message & ")")
                    End Try
                End If
            End If
        End If
        ' If no new name found: check if the link's parameters are actually consumed.
        ' If source file also doesn't exist AND no parameters are consumed → delete
        ' the link (it's an orphaned external reference with no live connections).
        If sNewFullName = "" Then
            Dim bSourceExists As Boolean = System.IO.File.Exists(sRefFullName)
            If Not bSourceExists Then
                ' Source gone - check if any parameters from this table are consumed
                Dim bAnyConsumed As Boolean = False
                Try
                    For j As Integer = oTables.Count To 1 Step -1
                        Dim oChkTable As Object = oTables.Item(j)
                        Dim sChkName As String = ""
                        Try : sChkName = oChkTable.ReferencedDocumentDescriptor.FullDocumentName : Catch : End Try
                        If String.Compare(sChkName, sRefFullName, True) = 0 Then
                            Try
                                For Each oParam As Object In oChkTable
                                    Try
                                        If oParam.IsConsumed Then
                                            bAnyConsumed = True
                                            Exit For
                                        End If
                                    Catch
                                    End Try
                                Next
                            Catch
                            End Try
                        End If
                    Next
                Catch
                End Try
                If Not bAnyConsumed Then
                    ' No consumed parameters and source gone - safe to delete the link
                    Try
                        oTable.Delete()
                        iCount = iCount + 1
                        bChanged = True
                        oLog.Append(vbCrLf & "  PARAM TABLE (dead link - source gone, no consumed params, deleted): " & sDocName & " -> " & System.IO.Path.GetFileName(sRefFullName))
                    Catch exDL As Exception
                        oLog.Append(vbCrLf & "  PARAM TABLE (dead link delete FAILED): " & sDocName & " -> " & System.IO.Path.GetFileName(sRefFullName) & " (" & exDL.Message & ")")
                    End Try
                Else
                    oLog.Append(vbCrLf & "  PARAM TABLE (source missing, params ARE consumed - manual fix needed): " & sDocName & " -> " & System.IO.Path.GetFileName(sRefFullName))
                End If
            End If
            Continue For  ' not in rename map and no Find/Replace match
        End If
        If String.Compare(sNewFullName, sRefFullName, True) = 0 Then Continue For  ' same name, same folder - already correct

        If Not System.IO.File.Exists(sNewFullName) Then
            ' Target renamed file doesn't exist yet. Check if the SOURCE also
            ' doesn't exist - if so, the link is ORPHANED (broken reference to
            ' a file that was never copied to the target folder and isn't
            ' accessible anywhere). Inventor shows these as unresolved (+).
            ' If the parameters it drove are unused, the link is safe to delete.
            ' DELETE orphaned links rather than leaving them broken forever.
            Dim bSourceMissing As Boolean = Not System.IO.File.Exists(sRefFullName)
            If bSourceMissing Then
                ' Orphaned link - source gone, target never created. Delete it.
                ' Clear read-only on doc first.
                Try
                    Dim oOrphanAttrs As System.IO.FileAttributes = System.IO.File.GetAttributes(oDoc.FullFileName)
                    If (oOrphanAttrs And System.IO.FileAttributes.ReadOnly) = System.IO.FileAttributes.ReadOnly Then
                        System.IO.File.SetAttributes(oDoc.FullFileName, oOrphanAttrs And Not System.IO.FileAttributes.ReadOnly)
                    End If
                Catch
                End Try
                Try
                    oTable.Delete()
                    iCount = iCount + 1
                    bChanged = True
                    oLog.Append(vbCrLf & "  PARAM TABLE (orphaned - source missing, deleted link): " & sDocName & " -> " & System.IO.Path.GetFileName(sRefFullName))
                Catch exDel As Exception
                    oLog.Append(vbCrLf & "  PARAM TABLE (orphaned) delete FAILED in " & sDocName & ": " & System.IO.Path.GetFileName(sRefFullName) & " (" & exDel.Message & ")")
                    If oNeedsCheckout IsNot Nothing Then oNeedsCheckout.Add(oDoc.FullFileName)
                End Try
            Else
                ' Source exists but renamed target not yet on disk.
                ' Run TRAVERSE Mode 1 first to create the renamed copy, then re-run.
                oLog.Append(vbCrLf & "  PARAM TABLE (renamed): target not yet on disk - " & sDocName & " -> " & System.IO.Path.GetFileName(sNewFullName) & " (source exists; run TRAVERSE to create renamed copy first)")
            End If
            Continue For
        End If

        ' --- Pre-check: if the assembly is read-only on disk (checked in to
        ' Vault), both ReplaceReference and Delete+Add will throw E_FAIL because
        ' Vault intercepts those COM calls at the API level - not just the file
        ' system level. Clearing the attribute bypasses the filesystem lock but
        ' NOT the Vault COM interception. Skip the attempt entirely and
        ' accumulate the file in oNeedsCheckout so the user gets a clear list
        ' of files to check out before re-running.
        Dim bDocIsReadOnly As Boolean = False
        Try
            Dim oDocAttrs As System.IO.FileAttributes = System.IO.File.GetAttributes(oDoc.FullFileName)
            bDocIsReadOnly = ((oDocAttrs And System.IO.FileAttributes.ReadOnly) = System.IO.FileAttributes.ReadOnly)
            If Not bDocIsReadOnly Then
                ' Not read-only on disk - clear anyway in case of partial locks
                System.IO.File.SetAttributes(oDoc.FullFileName, oDocAttrs And Not System.IO.FileAttributes.ReadOnly)
            End If
        Catch
        End Try

        If bDocIsReadOnly Then
            oLog.Append(vbCrLf & "  PARAM TABLE (renamed) SKIPPED - file is READ-ONLY: " & sDocName & " -> " & System.IO.Path.GetFileName(sRefFullName) & "  [will retry on next run when file is writable]")
            If oNeedsCheckout IsNot Nothing Then oNeedsCheckout.Add(oDoc.FullFileName)
            Continue For
        End If

        Dim bDone As Boolean = False
        Try
            oTable.ReferencedDocumentDescriptor.ReferencedFileDescriptor.ReplaceReference(sNewFullName)
            If String.Compare(oTable.ReferencedDocumentDescriptor.FullDocumentName, sNewFullName, True) = 0 Then
                bDone = True
            End If
        Catch
        End Try

        If Not bDone Then
            Try
                oTable.Delete()
                oTables.Add(sNewFullName)
                bDone = True
            Catch ex As Exception
                oLog.Append(vbCrLf & "  PARAM TABLE (renamed) relink FAILED in " & sDocName & ": " & System.IO.Path.GetFileName(sRefFullName) & " (" & ex.Message & ")")
                ' E_FAIL here even though the file wasn't read-only on disk means
                ' Vault is intercepting the COM call. Add to checkout list.
                If oNeedsCheckout IsNot Nothing Then oNeedsCheckout.Add(oDoc.FullFileName)
            End Try
        End If

        If bDone Then
            iCount = iCount + 1
            bChanged = True
            oLog.Append(vbCrLf & "  PARAM TABLE (renamed) updated in " & sDocName & ": " & System.IO.Path.GetFileName(sRefFullName) & "  -->  " & System.IO.Path.GetFileName(sNewFullName))
        End If
    Next

    ' =====================================================================
    ' EXCEL / SPREADSHEET ParameterTables (separate collection from
    ' DerivedParameterTables). These use ParameterTable.FileName for the
    ' linked path - NOT ReferencedDocumentDescriptor. Without this block the
    ' top assembly (and any part) keeps pointing at the OLD project folder's
    ' .xlsx even after the new-named copies land in sTargetFolder.
    ' =====================================================================
    Try
        Dim oExcelTables As ParameterTables = Nothing
        Try
            oExcelTables = oDoc.ComponentDefinition.Parameters.ParameterTables
        Catch
            oExcelTables = Nothing
        End Try

        If oExcelTables IsNot Nothing AndAlso oExcelTables.Count > 0 Then
            For iX As Integer = oExcelTables.Count To 1 Step -1
                Dim oXTable As ParameterTable = Nothing
                Try
                    oXTable = oExcelTables.Item(iX)
                Catch
                    Continue For
                End Try
                If oXTable Is Nothing Then Continue For

                ' Only linked tables can be retargeted; embedded ones have no external path
                Dim bIsLinked As Boolean = False
                Try
                    bIsLinked = oXTable.Linked
                Catch
                    bIsLinked = False
                End Try
                If Not bIsLinked Then Continue For

                Dim sXRefFull As String = ""
                Try
                    sXRefFull = oXTable.FileName
                Catch
                    sXRefFull = ""
                End Try
                If Trim(sXRefFull) = "" Then Continue For

                Dim sXNewFull As String = ""

                ' 1) Already in rename map?
                For Each kvpX As System.Collections.Generic.KeyValuePair(Of String, String) In oRenameMap
                    If String.Compare(kvpX.Key, sXRefFull, True) = 0 Then
                        sXNewFull = kvpX.Value
                        Exit For
                    End If
                Next

                ' 2) Find/Replace pattern - look for renamed (or same-name local) copy in target folder
                If sXNewFull = "" AndAlso sFind <> "" AndAlso sTargetFolder <> "" Then
                    Dim sXName As String = System.IO.Path.GetFileNameWithoutExtension(sXRefFull)
                    Dim sXExt As String = System.IO.Path.GetExtension(sXRefFull)
                    Dim bXMatch As Boolean
                    If bUseContainsMode Then
                        bXMatch = sXName.ToUpper().Contains(sFind.ToUpper())
                    Else
                        bXMatch = sXName.ToUpper().StartsWith(sFind.ToUpper())
                    End If
                    If bXMatch Then
                        Dim sXNewName As String
                        If bUseContainsMode Then
                            sXNewName = ReplaceAllCaseInsensitive(sXName, sFind, sReplace)
                        Else
                            sXNewName = sReplace & sXName.Substring(sFind.Length)
                        End If
                        Dim sXCandidate As String = System.IO.Path.Combine(sTargetFolder, sXNewName & sXExt)
                        If System.IO.File.Exists(sXCandidate) Then
                            sXNewFull = sXCandidate
                        ElseIf String.Compare(sXName, sXNewName, True) = 0 Then
                            ' Localize without renaming: same name, different folder
                            Dim sXSameLocal As String = System.IO.Path.Combine(sTargetFolder, sXName & sXExt)
                            If System.IO.File.Exists(sXSameLocal) AndAlso String.Compare(sXSameLocal, sXRefFull, True) <> 0 Then
                                sXNewFull = sXSameLocal
                            End If
                        End If
                    End If
                End If

                ' 3) Same filename already sitting in target folder (Copy Design left name unchanged)
                If sXNewFull = "" AndAlso sTargetFolder <> "" Then
                    Dim sXJustName As String = System.IO.Path.GetFileName(sXRefFull)
                    Dim sXLocal As String = System.IO.Path.Combine(sTargetFolder, sXJustName)
                    If System.IO.File.Exists(sXLocal) AndAlso String.Compare(sXLocal, sXRefFull, True) <> 0 Then
                        sXNewFull = sXLocal
                    End If
                End If

                ' 4) Match found but target not on disk yet - File.Copy the Excel into target
                If sXNewFull = "" AndAlso sFind <> "" AndAlso sTargetFolder <> "" Then
                    Dim sXName2 As String = System.IO.Path.GetFileNameWithoutExtension(sXRefFull)
                    Dim sXExt2 As String = System.IO.Path.GetExtension(sXRefFull)
                    Dim bXMatch2 As Boolean
                    If bUseContainsMode Then
                        bXMatch2 = sXName2.ToUpper().Contains(sFind.ToUpper())
                    Else
                        bXMatch2 = sXName2.ToUpper().StartsWith(sFind.ToUpper())
                    End If
                    If bXMatch2 AndAlso System.IO.File.Exists(sXRefFull) Then
                        Dim sXNewName2 As String
                        If bUseContainsMode Then
                            sXNewName2 = ReplaceAllCaseInsensitive(sXName2, sFind, sReplace)
                        Else
                            sXNewName2 = sReplace & sXName2.Substring(sFind.Length)
                        End If
                        Dim sXDest As String = System.IO.Path.Combine(sTargetFolder, sXNewName2 & sXExt2)
                        If Not System.IO.File.Exists(sXDest) Then
                            Try
                                System.IO.File.Copy(sXRefFull, sXDest, False)
                                Try
                                    Dim oXAttr As System.IO.FileAttributes = System.IO.File.GetAttributes(sXDest)
                                    If (oXAttr And System.IO.FileAttributes.ReadOnly) = System.IO.FileAttributes.ReadOnly Then
                                        System.IO.File.SetAttributes(sXDest, oXAttr And Not System.IO.FileAttributes.ReadOnly)
                                    End If
                                Catch
                                End Try
                                oLog.Append(vbCrLf & "  EXCEL PARAM TABLE copied to target: " & sXName2 & sXExt2 & "  -->  " & sXNewName2 & sXExt2)
                            Catch exXC As Exception
                                oLog.Append(vbCrLf & "  EXCEL PARAM TABLE copy FAILED: " & sXName2 & sXExt2 & " (" & exXC.Message & ")")
                            End Try
                        End If
                        If System.IO.File.Exists(sXDest) Then sXNewFull = sXDest
                    End If
                End If

                If sXNewFull = "" Then Continue For
                If String.Compare(sXNewFull, sXRefFull, True) = 0 Then Continue For
                If Not System.IO.File.Exists(sXNewFull) Then
                    oLog.Append(vbCrLf & "  EXCEL PARAM TABLE: target not on disk yet - " & sDocName & " -> " & System.IO.Path.GetFileName(sXNewFull))
                    Continue For
                End If

                ' Clear read-only on host doc before changing the link
                Try
                    Dim oXA As System.IO.FileAttributes = System.IO.File.GetAttributes(oDoc.FullFileName)
                    If (oXA And System.IO.FileAttributes.ReadOnly) = System.IO.FileAttributes.ReadOnly Then
                        System.IO.File.SetAttributes(oDoc.FullFileName, oXA And Not System.IO.FileAttributes.ReadOnly)
                    End If
                Catch
                End Try

                Dim bXDone As Boolean = False
                Try
                    ' Preferred API for linked Excel tables
                    oXTable.FileName = sXNewFull
                    If String.Compare(oXTable.FileName, sXNewFull, True) = 0 Then bXDone = True
                Catch
                End Try

                If Not bXDone Then
                    Try
                        If oXTable.ReferencedFileDescriptor IsNot Nothing Then
                            oXTable.ReferencedFileDescriptor.ReplaceReference(sXNewFull)
                            bXDone = True
                        End If
                    Catch
                    End Try
                End If

                If bXDone Then
                    oRenameMap(sXRefFull) = sXNewFull
                    iCount = iCount + 1
                    bChanged = True
                    oLog.Append(vbCrLf & "  EXCEL PARAM TABLE updated in " & sDocName & ": " & System.IO.Path.GetFileName(sXRefFull) & "  -->  " & System.IO.Path.GetFileName(sXNewFull))
                Else
                    oLog.Append(vbCrLf & "  EXCEL PARAM TABLE relink FAILED in " & sDocName & ": " & System.IO.Path.GetFileName(sXRefFull))
                    If oNeedsCheckout IsNot Nothing Then oNeedsCheckout.Add(oDoc.FullFileName)
                End If
            Next
        End If
    Catch exExcel As Exception
        oLog.Append(vbCrLf & "  EXCEL PARAM TABLE pass error in " & sDocName & ": " & exExcel.Message)
    End Try

    Return bChanged

End Function



' True if sFullName is already inside the target folder tree -
' i.e. a local copy safe to modify in place. Files outside the
' target folder are Vault-managed originals that must be localized first.
' NOTE: The original top assembly is NOT considered safe here — in Mode 6
' (Copy Design) it must never be mutated; only the NEW copy in sTargetFolder
' returns True (via the folder check below).
Function IsDocSafeToMutate(sFullName As String, sTargetFolder As String, sTopAssemblyFullName As String) As Boolean
    If Trim(sFullName) = "" Then Return False
    Try
        Dim sFolder As String = System.IO.Path.GetDirectoryName(sFullName)
        Dim sTargetU As String = sTargetFolder.TrimEnd(System.IO.Path.DirectorySeparatorChar).ToUpper()
        Dim sFolderU As String = sFolder.TrimEnd(System.IO.Path.DirectorySeparatorChar).ToUpper()
        If sFolderU = sTargetU Then Return True
        If sFolderU.StartsWith(sTargetU & System.IO.Path.DirectorySeparatorChar) Then Return True
        Dim sNonStd As String = System.IO.Path.Combine(sTargetFolder, "Non Std Parts").TrimEnd(System.IO.Path.DirectorySeparatorChar).ToUpper()
        If sFolderU = sNonStd OrElse sFolderU.StartsWith(sNonStd & System.IO.Path.DirectorySeparatorChar) Then Return True
    Catch
    End Try
    Return False
End Function

' Quick identity check used by the collision guard.
' Returns True if the two files appear to be the same item (same size).
' Used to decide whether a rename target that already exists can be reused
' or whether we must append _Duplicate instead.
Function FilesAppearIdentical(sPathA As String, sPathB As String) As Boolean
    Try
        If Not System.IO.File.Exists(sPathA) OrElse Not System.IO.File.Exists(sPathB) Then Return False
        Dim oInfoA As New System.IO.FileInfo(sPathA)
        Dim oInfoB As New System.IO.FileInfo(sPathB)
        ' Same length is treated as identical for this purpose.
        ' A full geometry compare is too expensive inside the map builder.
        Return (oInfoA.Length = oInfoB.Length)
    Catch
        Return False
    End Try
End Function

' Given a proposed name like "PJ00444-3450-6-V0-04-009", find the highest
' existing trailing number in the same sequence (e.g. V0-04-099) and return
' the next free name (e.g. PJ00444-3450-6-V0-04-100).
' Falls back to _Duplicate only if the name has no trailing -digits pattern.
Function NextFreeSequenceName(sFolder As String, sProposedBase As String, sExt As String, Optional oClaimed As System.Collections.Generic.HashSet(Of String) = Nothing) As String
    Try
        ' Match a trailing -digits (the sequence number)
        Dim oMatch As System.Text.RegularExpressions.Match = _
            System.Text.RegularExpressions.Regex.Match(sProposedBase, "-(\d+)$")
        If Not oMatch.Success Then
            ' No sequence pattern — fall back to _Duplicate
            Return sProposedBase & "_Duplicate"
        End If
        Dim sPrefix As String = sProposedBase.Substring(0, oMatch.Index)   ' everything before the final -NNN
        Dim iWidth As Integer = oMatch.Groups(1).Value.Length               ' preserve zero-padding width
        Dim iMax As Integer = 0

        ' Scan the folder for files that share the same prefix and have a trailing number
        Dim sPattern As String = sPrefix & "-*" & sExt
        Try
            For Each sFile As String In System.IO.Directory.GetFiles(sFolder, sPattern)
                Dim sBase As String = System.IO.Path.GetFileNameWithoutExtension(sFile)
                Dim oM As System.Text.RegularExpressions.Match = _
                    System.Text.RegularExpressions.Regex.Match(sBase, "-(\d+)$")
                If oM.Success AndAlso sBase.StartsWith(sPrefix & "-", StringComparison.OrdinalIgnoreCase) Then
                    Dim iNum As Integer = 0
                    If Integer.TryParse(oM.Groups(1).Value, iNum) Then
                        If iNum > iMax Then iMax = iNum
                    End If
                End If
            Next
        Catch : End Try

        ' Also consider names already claimed in the current map (not yet on disk)
        If oClaimed IsNot Nothing Then
            For Each sClaimedFull As String In oClaimed
                Dim sBase As String = System.IO.Path.GetFileNameWithoutExtension(sClaimedFull)
                Dim oM As System.Text.RegularExpressions.Match = _
                    System.Text.RegularExpressions.Regex.Match(sBase, "-(\d+)$")
                If oM.Success AndAlso sBase.StartsWith(sPrefix & "-", StringComparison.OrdinalIgnoreCase) Then
                    Dim iNum As Integer = 0
                    If Integer.TryParse(oM.Groups(1).Value, iNum) Then
                        If iNum > iMax Then iMax = iNum
                    End If
                End If
            Next
        End If

        Dim iNext As Integer = iMax + 1
        Dim sNextNum As String = iNext.ToString().PadLeft(iWidth, "0"c)
        Return sPrefix & "-" & sNextNum
    Catch
        Return sProposedBase & "_Duplicate"
    End Try
End Function

' True if sFullPath sits inside one of the always-excluded folders -
' Vault Libraries, Content Center Files\en-US, or the Jameson Cell
' SJD00-GT Standard project folder. Checked as a case-insensitive
' substring match against the full path.
Function IsInExcludedFolder(sFullPath As String) As Boolean
    Dim sUpper As String = sFullPath.ToUpper()
    ' Only exclude the DEDICATED SJD00-GT Standard project folder -
    ' NOT SJD00-GT subfolders inside other project folders (e.g. PJ00141).
    ' The dedicated folder sits directly under Jameson Cell with no other
    ' project folder in between.
    If sUpper.Contains("VAULT\PROJECTS\JAMESON CELL\SJD00-GT STANDARD\") Then Return True
    ' Only exclude files physically inside VAULT\LIBRARIES\ - not project copies
    If sUpper.Contains("VAULT\LIBRARIES\\") Then Return True
    ' Only exclude the GLOBAL Vault Content Center root folder.
    ' Project-specific "Content Center Files" subfolders (e.g. PJ00193.../Content Center Files/)
    ' are project-owned copies and must be renamed/repointed like any other project file.
    ' The global CC root always contains "VAULT\CONTENT CENTER FILES" directly (not under a project).
    If sUpper.Contains("VAULT\CONTENT CENTER FILES") Then Return True
    ' Do NOT exclude \CONTENT CENTER FILES\ as a generic substring — that would
    ' incorrectly catch project-specific CC subfolders (PJ00193.../Content Center Files/).
    Return False
End Function


' Content Center = physically in the GLOBAL CC Files folder.
' A part originally from CC that has been copied into a project-specific
' "Content Center Files" subfolder is no longer excluded — it is a project copy
' that needs renaming/repointing like any other project file.
Function IsContentCenterMember(oDoc As Document) As Boolean
    Try
        Dim sFull As String = oDoc.FullFileName
        If sFull = "" Then Return False
        Dim sUpper As String = sFull.ToUpper()
        ' Only exclude files physically in the GLOBAL Vault Content Center root.
        ' Project-specific "Content Center Files" subfolders are project copies.
        If Not sUpper.Contains("VAULT\CONTENT CENTER FILES") Then Return False
        Return True
    Catch
    End Try
    Return False
End Function


' True if sFullPath is a SYNTHETIC name Inventor generates for certain
' pattern-member occurrences (e.g. a Component Pattern element) instead
' of a real file path - observed in testing as
' "<host assembly name>$<digits>$<underlying part name>.ipt", such as
' "PJ00184-GTA-3250-6-00120$0$M20x60.ipt". This is NOT a real file on
' disk; it's Inventor's own internal representation for that specific
' occurrence.
'
' IMPORTANT: the "$<digits>$" pattern alone isn't a reliable enough
' signal on its own - a GENUINELY REAL, saved file can also legitimately
' contain "$0$" in its actual name for a completely different reason
' (e.g. an artifact of a CAD interop import), and that kind of file
' SHOULD be available to ordinary rename/Find-Replace processing like
' any other file, not silently skipped forever. So this only returns
' True when the pattern matches AND no real file exists at this exact
' path - i.e. it's the bogus runtime-only case, not a real file that
' merely happens to look similar. A real file matching the pattern
' returns False here and is treated completely normally.
Function IsSyntheticPatternMemberName(sFullPath As String) As Boolean
    Try
        If Not System.Text.RegularExpressions.Regex.IsMatch(sFullPath, "\$\d+\$") Then Return False
        If System.IO.File.Exists(sFullPath) Then Return False ' a real file exists here - treat normally, not as a bogus synthetic path
        Return True
    Catch
        Return False
    End Try
End Function


' ---------------------------------------------------------------------
' ---------------------------------------------------------------------
' POST-TRAVERSAL DERIVED/PARAM PASS
' Walks every document in the tree via AllReferencedDocuments (which
' handles dedup and cycles internally) and runs the three-pass derived
' source / param table fix on each one. This catches documents that the
' performance cache in ProcessLevel short-circuited before their
' ProcessDerivedSource / UpdateLinkedParamsAfterRename calls were reached.
' Classic example: a part like PJ00888-3250-00-01-V04-01-000S.ipt whose
' parent assembly was cached as "nothing changed" on a previous branch,
' so ProcessLevel returned early and never checked its derived sources.
' This pass runs unconditionally on Mode 1/2 after the main traversal,
' and is a no-op on any document whose references are already correct.
' ---------------------------------------------------------------------
Sub RunDerivedAndParamFixPass(oAsmDoc As AssemblyDocument, sFind As String, sReplace As String, bUseContainsMode As Boolean, sTargetFolder As String, ByRef oRenameMap As System.Collections.Generic.Dictionary(Of String, String), oLog As System.Text.StringBuilder, ByRef iCount As Integer, ByRef oNeedsCheckout As System.Collections.Generic.HashSet(Of String), sLogFilePath As String)

    Dim oSavedInPass As New System.Collections.Generic.HashSet(Of String)

    For Each oRefDoc As Document In oAsmDoc.AllReferencedDocuments

        If oRefDoc.DocumentType <> kPartDocumentObject AndAlso oRefDoc.DocumentType <> kAssemblyDocumentObject Then Continue For

        Dim sFullName As String = ""
        Try
            sFullName = oRefDoc.FullFileName
        Catch
            Continue For
        End Try

        If Trim(sFullName) = "" Then Continue For
        If sFullName.Contains("*") Then Continue For
        If IsSyntheticPatternMemberName(sFullName) Then Continue For
        If IsInExcludedFolder(sFullName) Then Continue For
        If IsContentCenterMember(oRefDoc) Then Continue For

        Dim bDocChanged As Boolean = False

        ' FIX 1 - SAFETY GUARD: only fix derive sources and param links on
        ' documents already in the target folder. AllReferencedDocuments
        ' includes originals still in the Vault project folder - calling
        ' ReplaceReference on those modifies them on disk, contaminating
        ' the source project (the screenshots showed PJ00999 refs appearing
        ' inside PJ00174 originals). IsDocSafeToMutate returns True only
        ' for files inside the target folder tree.
        If Not IsDocSafeToMutate(sFullName, sTargetFolder, oAsmDoc.FullFileName) Then
            Continue For  ' original Vault file - never mutate it here
        End If

        ' FIX 2 - CROSS-PROJECT CONTAINER GUARD: In a cross-project derived pass
        ' (bUseContainsMode=False, sFind <> sReplace), cross-project files (e.g. PJ00180-*)
        ' are copied to the target folder with their original names unchanged.
        ' IsDocSafeToMutate passes for them (they ARE in the target folder).
        ' But if we update their internal derived sources without first renaming the
        ' container, we get a corrupted file: PJ00180 shell pointing to PJ00555 geometry.
        ' Rule: only touch the derived sources of files whose name starts with sReplace
        ' (i.e. the new-prefix copies). Leave sFind-prefix containers untouched.
        If Not bUseContainsMode AndAlso String.Compare(sFind, sReplace, True) <> 0 Then
            Dim sFileBase As String = System.IO.Path.GetFileNameWithoutExtension(sFullName)
            Dim sCheckPrefix As String = sFind.ToUpper() & "-"
            Dim sCheckPrefix2 As String = sFind.ToUpper() & "_"
            If sFileBase.ToUpper().StartsWith(sCheckPrefix) OrElse sFileBase.ToUpper().StartsWith(sCheckPrefix2) Then
                Try : System.IO.File.AppendAllText(sLogFilePath, "  DERIVED PASS SKIP (cross-project container not yet renamed): " & System.IO.Path.GetFileName(sFullName) & vbCrLf) : Catch : End Try
                Continue For  ' shared cross-project file - never modify its internal references
            End If
        End If

        ' --- Bolted Connection assemblies: file descriptor repointing ---
        ' DA-managed fastener occurrences cannot be replaced via the normal
        ' ComponentOccurrence API. ProcessBoltedConnectionRefs uses
        ' File.ReferencedFileDescriptors which bypasses DA protection.
        If oRefDoc.DocumentType = kAssemblyDocumentObject AndAlso _
           IsBoltedConnectionAssembly(oRefDoc.ComponentDefinition) Then
            Try
                If ProcessBoltedConnectionRefs(oRefDoc, sFind, sReplace, bUseContainsMode, sTargetFolder, oLog, iCount, oRenameMap) Then
                    bDocChanged = True
                End If
            Catch ex As Exception
                oLog.Append(vbCrLf & "BOLTED-CONN PASS: failed on " & System.IO.Path.GetFileName(sFullName) & ": " & ex.Message)
            End Try
        End If

        ' --- Parts: derived file refs + BaseComponent + param tables ---
        If oRefDoc.DocumentType = kPartDocumentObject Then
            Try
                If ProcessDerivedSource(oRefDoc, sFind, sReplace, bUseContainsMode, sTargetFolder, oAsmDoc.FullFileName, oLog, iCount, oRenameMap, sLogFilePath) Then
                    bDocChanged = True
                    ' CRITICAL: save after derive repoint BEFORE param table relink.
                    ' Inventor blocks DerivedParameterTables ReplaceReference with
                    ' E_FAIL when the host part is still dirty from an uncommitted
                    ' derive source repoint. Saving here commits it first.
                    If Not oSavedInPass.Contains(sFullName) Then
                        Try
                            Dim oPreSA As System.IO.FileAttributes = System.IO.File.GetAttributes(sFullName)
                            If (oPreSA And System.IO.FileAttributes.ReadOnly) = System.IO.FileAttributes.ReadOnly Then
                                System.IO.File.SetAttributes(sFullName, oPreSA And Not System.IO.FileAttributes.ReadOnly)
                            End If
                        Catch
                        End Try
                        Try
                            oRefDoc.Save2(False)
                            oSavedInPass.Add(sFullName)
                            oLog.Append(vbCrLf & "  DERIVED/PARAM PASS: saved after derive repoint (before param table relink): " & System.IO.Path.GetFileName(sFullName))
                        Catch exPreSave As Exception
                            oLog.Append(vbCrLf & "  DERIVED/PARAM PASS: pre-relink save failed for " & System.IO.Path.GetFileName(sFullName) & " (" & exPreSave.Message & ")")
                        End Try
                    End If
                End If
            Catch ex As Exception
                oLog.Append(vbCrLf & "DERIVED PASS: failed on " & System.IO.Path.GetFileName(sFullName) & ": " & ex.Message)
            End Try
        End If

        ' --- Parts and assemblies: linked param table fixes ---
        Try
            If UpdateLinkedParamsAfterRename(oRefDoc, oRenameMap, oLog, iCount, sFind, sReplace, bUseContainsMode, sTargetFolder, oNeedsCheckout) Then
                bDocChanged = True
            End If
        Catch ex As Exception
            oLog.Append(vbCrLf & "PARAM PASS: failed on " & System.IO.Path.GetFileName(sFullName) & ": " & ex.Message)
        End Try

        ' --- Save if changed, once per document ---
        If bDocChanged AndAlso Not oSavedInPass.Contains(sFullName) Then
            Try
                Dim oSaveAttrs As System.IO.FileAttributes = System.IO.File.GetAttributes(sFullName)
                If (oSaveAttrs And System.IO.FileAttributes.ReadOnly) = System.IO.FileAttributes.ReadOnly Then
                    System.IO.File.SetAttributes(sFullName, oSaveAttrs And Not System.IO.FileAttributes.ReadOnly)
                End If
            Catch
            End Try
            Try
                oRefDoc.Save2(False)
                oSavedInPass.Add(sFullName)
                oLog.Append(vbCrLf & "  DERIVED/PARAM PASS: saved " & System.IO.Path.GetFileName(sFullName))
            Catch ex As Exception
                oLog.Append(vbCrLf & "  DERIVED/PARAM PASS: save failed for " & System.IO.Path.GetFileName(sFullName) & " (" & ex.Message & ")")
            End Try
        End If

    Next

End Sub


' ---------------------------------------------------------------------
' BROWSER NODE RESET PASS
' Resets every occurrence's browser display name to its actual filename.
' Clears stale Vault Copy Design labels so the renamed names show correctly.
' ---------------------------------------------------------------------
' Resets browser node names to Inventor "Default" behaviour (file name).
' Setting Occurrence.Name = "" clears any manual override - the same action
' as Assemble > Productivity > Rename Browser Nodes > Default > Apply.
' Falls back to explicit file name if a blank name is rejected (patterns/DA).
Sub RunBrowserNodeResetPass(oCompDef As ComponentDefinition, ByRef iReset As Integer)
    For Each oOcc As ComponentOccurrence In oCompDef.Occurrences
        Try
            If oOcc.Suppressed Then Continue For
            Dim sBefore As String = oOcc.Name
            Try
                oOcc.Name = ""
                If String.Compare(sBefore, oOcc.Name, True) <> 0 Then iReset = iReset + 1
            Catch
                ' Some pattern / DA instances reject a blank name - fall back
                ' to explicitly setting the file name without extension.
                Try
                    Dim sFullName As String = ""
                    Try : sFullName = oOcc.Definition.Document.FullFileName : Catch : End Try
                    If sFullName <> "" AndAlso Not sFullName.Contains("*") Then
                        Dim sCorrectName As String = System.IO.Path.GetFileNameWithoutExtension(sFullName)
                        If String.Compare(oOcc.Name, sCorrectName, True) <> 0 Then
                            oOcc.Name = sCorrectName
                            iReset = iReset + 1
                        End If
                    End If
                Catch
                End Try
            End Try
        Catch
        End Try
        Try
            Dim oSubDoc As Document = Nothing
            Try : oSubDoc = oOcc.Definition.Document : Catch : End Try
            If oSubDoc IsNot Nothing AndAlso oSubDoc.DocumentType = kAssemblyDocumentObject Then
                RunBrowserNodeResetPass(oOcc.Definition, iReset)
            End If
        Catch
        End Try
    Next
End Sub



' ---------------------------------------------------------------------
' FIX INTERNAL REFS PASS
' Walks every document in AllReferencedDocuments and runs three passes
' on each, mirroring the standalone Fix_Internal_References rule.
' Uses each document's OWN FOLDER as the target so documents in
' subfolders (frame members, Non Std Parts etc.) resolve correctly.
'
' Pass 1: DerivedParameterTables (linked param xlsx/ipt) - copy if needed,
'         delete+re-add fallback if ReplaceReference fails.
' Pass 2: File.ReferencedFileDescriptors (derive sources, xlsx at file level)
' Pass 3: BaseComponent / PartComponentDefinition derive sources
'
' Runs AFTER RunDerivedAndParamFixPass so oRenameMap already contains
' all renames from the main traversal.
' ---------------------------------------------------------------------
Sub RunFixInternalRefsPass(oAsmDoc As AssemblyDocument, sFind As String, sReplace As String, _
    bUseContainsMode As Boolean, sTargetFolder As String, _
    ByRef oRenameMap As System.Collections.Generic.Dictionary(Of String, String), _
    oLog As System.Text.StringBuilder, ByRef iCount As Integer, sLogFilePath As String)

    Dim oSavedInPass As New System.Collections.Generic.HashSet(Of String)(StringComparer.OrdinalIgnoreCase)

    For Each oRefDoc As Document In oAsmDoc.AllReferencedDocuments

        If oRefDoc.DocumentType <> kPartDocumentObject AndAlso _
           oRefDoc.DocumentType <> kAssemblyDocumentObject Then Continue For

        Dim sDocFull As String = ""
        Try : sDocFull = oRefDoc.FullFileName : Catch : Continue For : End Try
        If Trim(sDocFull) = "" Then Continue For
        If IsInExcludedFolder(sDocFull) Then Continue For
        If IsContentCenterMember(oRefDoc) Then Continue For

        ' SAFETY GUARD: only fix internal refs on documents already in the
        ' target folder tree. AllReferencedDocuments includes originals still
        ' in the Vault project folder (PJ00174, PJ00145 etc.) - calling
        ' ReplaceReference on those would contaminate the source project by
        ' writing PJ00999 xlsx links into files we never copied.
        ' IsDocSafeToMutate returns True only for files inside sTargetFolder.
        If Not IsDocSafeToMutate(sDocFull, sTargetFolder, oAsmDoc.FullFileName) Then
            Continue For  ' original Vault file - never mutate it here
        End If

        ' Use this document's OWN FOLDER as target - handles subfolders correctly
        Dim sDocFolder As String = System.IO.Path.GetDirectoryName(sDocFull)
        Dim sDocName   As String = System.IO.Path.GetFileName(sDocFull)
        Dim bDocChanged As Boolean = False

        ' ── PASS 1: DerivedParameterTables ──────────────────────────────
        Dim oAllCollections As New System.Collections.Generic.List(Of Object)
        Try
            Dim oDPT As Object = oRefDoc.ComponentDefinition.Parameters.DerivedParameterTables
            If oDPT IsNot Nothing AndAlso oDPT.Count > 0 Then oAllCollections.Add(oDPT)
        Catch : End Try
        If oRefDoc.DocumentType = kAssemblyDocumentObject Then
            Try
                Dim oPS As Object = oRefDoc.ComponentDefinition.Parameters.ParameterSets
                If oPS IsNot Nothing AndAlso oPS.Count > 0 Then oAllCollections.Add(oPS)
            Catch : End Try
        End If

        For Each oTables As Object In oAllCollections
            For i As Integer = oTables.Count To 1 Step -1
                Try
                    Dim oTable As Object = oTables.Item(i)
                    Dim sRefFull As String = ""
                    Try : sRefFull = oTable.ReferencedDocumentDescriptor.FullDocumentName : Catch : Continue For : End Try
                    If Trim(sRefFull) = "" OrElse IsInExcludedFolder(sRefFull) Then Continue For

                    Dim sRefName As String = System.IO.Path.GetFileNameWithoutExtension(sRefFull)
                    Dim sRefExt  As String = System.IO.Path.GetExtension(sRefFull)

                    ' Match?
                    Dim bMatch As Boolean
                    If bUseContainsMode Then
                        bMatch = sRefName.ToUpper().Contains(sFind.ToUpper())
                    Else
                        bMatch = sRefName.ToUpper().StartsWith(sFind.ToUpper())
                    End If
                    If Not bMatch Then Continue For

                    Dim sNewName As String
                    If bUseContainsMode Then
                        sNewName = ReplaceAllCaseInsensitive(sRefName, sFind, sReplace)
                    Else
                        sNewName = sReplace & sRefName.Substring(sFind.Length)
                    End If
                    Dim sNewFull As String = System.IO.Path.Combine(sDocFolder, sNewName & sRefExt)
                    If String.Compare(sRefFull, sNewFull, True) = 0 Then Continue For

                    ' Copy xlsx/csv to doc's own folder if missing (Frame Gen xlsx fix)
                    If Not System.IO.File.Exists(sNewFull) AndAlso System.IO.File.Exists(sRefFull) Then
                        Dim sExtU As String = sRefExt.ToUpper()
                        If sExtU = ".XLSX" OrElse sExtU = ".XLS" OrElse sExtU = ".CSV" Then
                            Try
                                System.IO.File.Copy(sRefFull, sNewFull, False)
                                oLog.Append(vbCrLf & "  INTERNAL-REFS PASS1 (xlsx copied): " & sDocName & " -> " & sNewName & sRefExt)
                            Catch : End Try
                        End If
                    End If

                    If Not System.IO.File.Exists(sNewFull) Then Continue For

                    ' Clear read-only on doc before modifying
                    Try
                        Dim oA As System.IO.FileAttributes = System.IO.File.GetAttributes(sDocFull)
                        If (oA And System.IO.FileAttributes.ReadOnly) = System.IO.FileAttributes.ReadOnly Then
                            System.IO.File.SetAttributes(sDocFull, oA And Not System.IO.FileAttributes.ReadOnly)
                        End If
                    Catch : End Try

                    ' Attempt 1: ReplaceReference
                    Dim bDone As Boolean = False
                    Try
                        oTable.ReferencedDocumentDescriptor.ReferencedFileDescriptor.ReplaceReference(sNewFull)
                        If String.Compare(oTable.ReferencedDocumentDescriptor.FullDocumentName, sNewFull, True) = 0 Then
                            bDone = True
                        End If
                    Catch : End Try

                    ' Attempt 2: Delete + re-add
                    If Not bDone Then
                        Try
                            oTable.Delete()
                            oTables.Add(sNewFull)
                            bDone = True
                        Catch : End Try
                    End If

                    If bDone Then
                        oRenameMap(sRefFull) = sNewFull
                        iCount = iCount + 1
                        bDocChanged = True
                        oLog.Append(vbCrLf & "  INTERNAL-REFS PASS1: " & sDocName & ": " & sRefName & sRefExt & "  -->  " & sNewName & sRefExt)
                    End If
                Catch : End Try
            Next
        Next

        ' ── PASS 2: File.ReferencedFileDescriptors ───────────────────────
        Try
            For Each oFD As FileDescriptor In oRefDoc.File.ReferencedFileDescriptors
                Try
                    Dim sRefFull As String = ""
                    Try : sRefFull = oFD.FullFileName : Catch : Continue For : End Try
                    If Trim(sRefFull) = "" OrElse IsInExcludedFolder(sRefFull) Then Continue For
                    If oRenameMap.ContainsKey(sRefFull) Then
                        Dim sKnown As String = oRenameMap(sRefFull)
                        If String.Compare(sKnown, sRefFull, True) <> 0 AndAlso System.IO.File.Exists(sKnown) Then
                            Try
                                Dim oA As System.IO.FileAttributes = System.IO.File.GetAttributes(sDocFull)
                                If (oA And System.IO.FileAttributes.ReadOnly) = System.IO.FileAttributes.ReadOnly Then System.IO.File.SetAttributes(sDocFull, oA And Not System.IO.FileAttributes.ReadOnly)
                            Catch : End Try
                            Try : oFD.ReplaceReference(sKnown) : bDocChanged = True : Catch : End Try
                        End If
                        Continue For
                    End If

                    Dim sRefName As String = System.IO.Path.GetFileNameWithoutExtension(sRefFull)
                    Dim sRefExt  As String = System.IO.Path.GetExtension(sRefFull)
                    Dim bMatch As Boolean
                    If bUseContainsMode Then
                        bMatch = sRefName.ToUpper().Contains(sFind.ToUpper())
                    Else
                        bMatch = sRefName.ToUpper().StartsWith(sFind.ToUpper())
                    End If
                    If Not bMatch Then Continue For

                    Dim sNewName As String
                    If bUseContainsMode Then
                        sNewName = ReplaceAllCaseInsensitive(sRefName, sFind, sReplace)
                    Else
                        sNewName = sReplace & sRefName.Substring(sFind.Length)
                    End If
                    Dim sNewFull As String = System.IO.Path.Combine(sDocFolder, sNewName & sRefExt)
                    If String.Compare(sRefFull, sNewFull, True) = 0 Then Continue For

                    ' Copy xlsx/csv if missing
                    If Not System.IO.File.Exists(sNewFull) AndAlso System.IO.File.Exists(sRefFull) Then
                        Dim sExtU As String = sRefExt.ToUpper()
                        If sExtU = ".XLSX" OrElse sExtU = ".XLS" OrElse sExtU = ".CSV" Then
                            Try : CopyXlsxSilently(sRefFull, sNewFull) : Catch : End Try
                        End If
                    End If
                    If Not System.IO.File.Exists(sNewFull) Then Continue For

                    Try
                        Dim oA As System.IO.FileAttributes = System.IO.File.GetAttributes(sDocFull)
                        If (oA And System.IO.FileAttributes.ReadOnly) = System.IO.FileAttributes.ReadOnly Then System.IO.File.SetAttributes(sDocFull, oA And Not System.IO.FileAttributes.ReadOnly)
                    Catch : End Try
                    Try
                        oFD.ReplaceReference(sNewFull)
                        oRenameMap(sRefFull) = sNewFull
                        iCount = iCount + 1
                        bDocChanged = True
                        oLog.Append(vbCrLf & "  INTERNAL-REFS PASS2: " & sDocName & ": " & sRefName & sRefExt & "  -->  " & sNewName & sRefExt)
                    Catch exFD As Exception
                        oLog.Append(vbCrLf & "  INTERNAL-REFS PASS2 FAILED: " & sDocName & ": " & sRefName & sRefExt & " (" & exFD.Message & ")")
                    End Try
                Catch : End Try
            Next
        Catch : End Try

        ' ── PASS 3: BaseComponent (PartComponentDefinition derive source) ─
        If oRefDoc.DocumentType = kPartDocumentObject Then
            Try
                Dim oPartDef As PartComponentDefinition = oRefDoc.ComponentDefinition
                If oPartDef.BaseComponent IsNot Nothing Then
                    Dim sBaseFull As String = ""
                    Try : sBaseFull = oPartDef.BaseComponent.Document.FullFileName : Catch : End Try
                    If sBaseFull <> "" AndAlso Not oRenameMap.ContainsKey(sBaseFull) Then
                        Dim sBaseName As String = System.IO.Path.GetFileNameWithoutExtension(sBaseFull)
                        Dim sBaseExt  As String = System.IO.Path.GetExtension(sBaseFull)
                        Dim bMatch As Boolean
                        If bUseContainsMode Then
                            bMatch = sBaseName.ToUpper().Contains(sFind.ToUpper())
                        Else
                            bMatch = sBaseName.ToUpper().StartsWith(sFind.ToUpper())
                        End If
                        If bMatch Then
                            Dim sBaseNew As String
                            If bUseContainsMode Then
                                sBaseNew = ReplaceAllCaseInsensitive(sBaseName, sFind, sReplace)
                            Else
                                sBaseNew = sReplace & sBaseName.Substring(sFind.Length)
                            End If
                            Dim sBaseNewFull As String = System.IO.Path.Combine(sDocFolder, sBaseNew & sBaseExt)
                            If String.Compare(sBaseFull, sBaseNewFull, True) <> 0 AndAlso System.IO.File.Exists(sBaseNewFull) Then
                                Try
                                    Dim oA As System.IO.FileAttributes = System.IO.File.GetAttributes(sDocFull)
                                    If (oA And System.IO.FileAttributes.ReadOnly) = System.IO.FileAttributes.ReadOnly Then System.IO.File.SetAttributes(sDocFull, oA And Not System.IO.FileAttributes.ReadOnly)
                                Catch : End Try
                                Dim bBaseFixed As Boolean = False
                                Try
                                    For Each oFD As FileDescriptor In oRefDoc.File.ReferencedFileDescriptors
                                        Try
                                            If String.Compare(oFD.FullFileName, sBaseFull, True) = 0 Then
                                                oFD.ReplaceReference(sBaseNewFull)
                                                bBaseFixed = True
                                                Exit For
                                            End If
                                        Catch : End Try
                                    Next
                                Catch : End Try
                                If bBaseFixed Then
                                    oRenameMap(sBaseFull) = sBaseNewFull
                                    iCount = iCount + 1
                                    bDocChanged = True
                                    oLog.Append(vbCrLf & "  INTERNAL-REFS PASS3: " & sDocName & ": " & sBaseName & sBaseExt & "  -->  " & sBaseNew & sBaseExt)
                                End If
                            End If
                        End If
                    End If
                End If
            Catch : End Try
        End If

        ' ── Save if changed ───────────────────────────────────────────────
        If bDocChanged AndAlso Not oSavedInPass.Contains(sDocFull) Then
            Try
                Dim oSA As System.IO.FileAttributes = System.IO.File.GetAttributes(sDocFull)
                If (oSA And System.IO.FileAttributes.ReadOnly) = System.IO.FileAttributes.ReadOnly Then System.IO.File.SetAttributes(sDocFull, oSA And Not System.IO.FileAttributes.ReadOnly)
            Catch : End Try
            Try
                oRefDoc.Save2(False)
                oSavedInPass.Add(sDocFull)
                oLog.Append(vbCrLf & "  INTERNAL-REFS PASS: saved " & sDocName)
            Catch exSave As Exception
                oLog.Append(vbCrLf & "  INTERNAL-REFS PASS: save FAILED for " & sDocName & " (" & exSave.Message & ")")
            End Try
        End If

    Next

End Sub


' PJ-NUMBER PROPERTY SYNC - added so a re-run (or the "localize without
' renaming" case, where Find and Replace are identical) also catches a
' STALE project number sitting inside a sub's Part Number or
' SPECIFICATION property value, left over from whatever project it
' originally came from. Deliberately a separate, self-contained pass
' (see the call site in Main) rather than woven into the recursive
' rename traversal above.
' ---------------------------------------------------------------------

' Returns the first "PJ" + one-or-more-digits token found in sText (case
' as typed, e.g. "PJ00194"), or "" if none is found. Digits stop
' naturally at the first non-digit character (a "-" or "_" or end of
' string), matching the requested "PJ number up to the next - or _"
' behaviour without needing to special-case those characters explicitly.
Function ExtractPjNumber(sText As String) As String
    Try
        Dim oMatch As System.Text.RegularExpressions.Match = System.Text.RegularExpressions.Regex.Match(sText, "PJ\d+", System.Text.RegularExpressions.RegexOptions.IgnoreCase)
        If oMatch.Success Then Return oMatch.Value
    Catch
    End Try
    Return ""
End Function


' Walks every part/sub-assembly referenced anywhere in oAsmDoc (via
' Inventor's own AllReferencedDocuments - handles dedup across shared
' components itself, no manual recursion needed here) and syncs the
' PJ-number property on every one whose FILE NAME currently contains
' sCurrentPjNumber.
Sub RunPjPropertySyncPass(oAsmDoc As AssemblyDocument, sCurrentPjNumber As String, _
    oSegFinds As System.Collections.Generic.List(Of String), _
    oSegReplaces As System.Collections.Generic.List(Of String), _
    oLog As System.Text.StringBuilder, ByRef iPropsUpdated As Integer)

    For Each oRefDoc As Document In oAsmDoc.AllReferencedDocuments

        If oRefDoc.DocumentType <> kPartDocumentObject AndAlso oRefDoc.DocumentType <> kAssemblyDocumentObject Then Continue For

        Dim sFullName As String = ""
        Try
            sFullName = oRefDoc.FullFileName
        Catch
            Continue For
        End Try

        If Trim(sFullName) = "" Then Continue For ' virtual component - no independent file
        If sFullName.Contains("*") Then Continue For ' virtual/private component pseudo-path
        If IsSyntheticPatternMemberName(sFullName) Then Continue For ' pattern-member synthetic name, not a real file

        If IsInExcludedFolder(sFullName) Then Continue For
        If IsContentCenterMember(oRefDoc) Then Continue For

        Dim sFileNameNoExt As String = System.IO.Path.GetFileNameWithoutExtension(sFullName)
        If Not sFileNameNoExt.ToUpper().Contains(sCurrentPjNumber.ToUpper()) Then Continue For

        SyncPjNumberInProperties(oRefDoc, sCurrentPjNumber, oSegFinds, oSegReplaces, oLog, iPropsUpdated)

    Next

End Sub


' On a single document: for "Part Number" (Design Tracking Properties)
' and "SPECIFICATION" (Inventor User Defined Properties, if present):
'
'   Rule 1 — If the value contains a PJ<digits> token AND that token is
'             not already sCurrentPjNumber, swap it (old PJ number → new).
'   Rule 2 — If the value contains sCurrentPjNumber (either already or
'             after Rule 1), also apply the segment find/replaces so the
'             rest of the string (e.g. "-343-V0-" → "-3431-6-V0-") matches
'             the renamed file.
'   Rule 3 — If the value has NO PJ<digits> token at all, leave it alone.
'
' Saves the document only if something actually changed.
Sub SyncPjNumberInProperties(oDoc As Document, sCurrentPjNumber As String, _
    oSegFinds As System.Collections.Generic.List(Of String), _
    oSegReplaces As System.Collections.Generic.List(Of String), _
    oLog As System.Text.StringBuilder, ByRef iPropsUpdated As Integer)

    Dim bAnyChanged As Boolean = False
    Dim sFileNameForLog As String = System.IO.Path.GetFileName(oDoc.FullFileName)

    ' Helper: apply PJ-number swap + segment replaces to one property value string.
    ' Returns the (possibly unchanged) new value.
    Dim ApplySync As Func(Of String, String) = Function(sVal As String) As String
        If Trim(sVal) = "" Then Return sVal
        ' Rule 3: no PJ token → leave alone
        If Not System.Text.RegularExpressions.Regex.IsMatch(sVal, "PJ\d+", System.Text.RegularExpressions.RegexOptions.IgnoreCase) Then Return sVal
        ' Rule 1: swap old PJ number → current
        Dim sResult As String = System.Text.RegularExpressions.Regex.Replace(sVal, "PJ\d+", sCurrentPjNumber, System.Text.RegularExpressions.RegexOptions.IgnoreCase)
        ' Rule 2: apply segment replaces (value now has current PJ number)
        If oSegFinds IsNot Nothing Then
            Dim iSeg As Integer
            For iSeg = 0 To oSegFinds.Count - 1
                Dim sSF As String = oSegFinds(iSeg)
                Dim sSR As String = ""
                If oSegReplaces IsNot Nothing AndAlso iSeg < oSegReplaces.Count Then sSR = oSegReplaces(iSeg)
                If Trim(sSF) <> "" AndAlso sResult.ToUpper().Contains(sSF.ToUpper()) Then
                    sResult = ReplaceAllCaseInsensitive(sResult, sSF, sSR)
                    ' Clean up any double-dashes or leading/trailing dashes left by blank replacements
                    Do While sResult.Contains("--") : sResult = sResult.Replace("--", "-") : Loop
                    sResult = sResult.Trim("-"c).Trim()
                End If
            Next
        End If
        Return sResult
    End Function

    Try
        Dim oDesignTrackingSet As PropertySet = oDoc.PropertySets.Item("Design Tracking Properties")
        Dim oPartNumProp As Inventor.Property = oDesignTrackingSet.Item("Part Number")
        Dim sCurrentVal As String = CStr(oPartNumProp.Value)
        Dim sNewVal As String = ApplySync(sCurrentVal)
        If String.Compare(sCurrentVal, sNewVal, False) <> 0 Then
            oPartNumProp.Value = sNewVal
            bAnyChanged = True
            iPropsUpdated = iPropsUpdated + 1
            oLog.Append(vbCrLf & "  PROP SYNC (Part Number) on " & sFileNameForLog & ": '" & sCurrentVal & "'  -->  '" & sNewVal & "'")
        End If
    Catch
        ' Part Number should always exist - if this fails, skip silently
    End Try

    Try
        Dim oCustomSet As PropertySet = oDoc.PropertySets.Item("Inventor User Defined Properties")
        Dim oSpecProp As Inventor.Property = Nothing
        Try
            oSpecProp = oCustomSet.Item("SPECIFICATION")
        Catch
            oSpecProp = Nothing ' property doesn't exist on this document - leave it alone
        End Try

        If oSpecProp IsNot Nothing Then
            Dim sCurrentSpecVal As String = CStr(oSpecProp.Value)
            Dim sNewSpecVal As String = ApplySync(sCurrentSpecVal)
            If String.Compare(sCurrentSpecVal, sNewSpecVal, False) <> 0 Then
                oSpecProp.Value = sNewSpecVal
                bAnyChanged = True
                iPropsUpdated = iPropsUpdated + 1
                oLog.Append(vbCrLf & "  PROP SYNC (SPECIFICATION) on " & sFileNameForLog & ": '" & sCurrentSpecVal & "'  -->  '" & sNewSpecVal & "'")
            End If
        End If
    Catch
        ' "Inventor User Defined Properties" set not found/accessible - skip silently
    End Try

    If bAnyChanged Then
        Try
            oDoc.Save2(False)
        Catch ex As Exception
            oLog.Append(vbCrLf & "  FAILED to save after property sync: " & sFileNameForLog & " (" & ex.Message & ")")
        End Try
    End If

End Sub


' Processes one level of the tree (a ComponentDefinition belonging to either
' the main assembly or a sub-assembly). Returns True if this level's own
' occurrence list was modified (i.e. one of its direct children got renamed),
' so the caller knows whether IT needs to re-save itself.
Function ProcessLevel(oCompDef As ComponentDefinition, sFind As String, sReplace As String, bUseContainsMode As Boolean, sTargetFolder As String, sTopAssemblyFullName As String, oLog As System.Text.StringBuilder, ByRef iCount As Integer, ByRef oRenameMap As System.Collections.Generic.Dictionary(Of String, String), ByRef oSavedInPlace As System.Collections.Generic.HashSet(Of String), ByRef oVisitedLevels As System.Collections.Generic.HashSet(Of String), ByRef oPathStack As System.Collections.Generic.List(Of String), ByRef oProcessedResults As System.Collections.Generic.Dictionary(Of String, Boolean), sLogFilePath As String, Optional bSkipCycleGuardEntry As Boolean = False, Optional ByRef oNeedsCheckout As System.Collections.Generic.HashSet(Of String) = Nothing, Optional oBatchAllFinds As System.Collections.Generic.List(Of String) = Nothing, Optional sAllReplace As String = "") As Boolean

    Dim bChangedHere As Boolean = False

    If IsExitRequested() Then Return False

    Dim sThisLevelFullName As String = oCompDef.Document.FullFileName

    ' --- Cycle guard (CURRENT PATH only, not "ever visited") ---
    ' A document used in more than one place in the tree (a shared
    ' bracket, standard sub-assembly, etc.) is normal and must be
    ' allowed to be entered again from a different branch - it's only a
    ' genuine cycle if a document is its own ANCESTOR on the current
    ' path. Removing the marker in the Finally block below (rather than
    ' leaving it forever) is what makes that distinction.
    '
    ' bSkipCycleGuardEntry is used when recursing into a VIRTUAL
    ' assembly - its FullFileName is intentionally identical to its
    ' immediate parent's (that's what makes it virtual), so it would
    ' always look like an instant "cycle" against the entry its own
    ' parent just added. Skipping the add/remove here (the parent's
    ' entry already covers this identity) lets its real, file-based
    ' children still be found and processed.
    If Not bSkipCycleGuardEntry Then
        If oVisitedLevels.Contains(sThisLevelFullName) Then
            oLog.Append(vbCrLf & "CYCLE DETECTED - refusing to re-enter: " & oCompDef.Document.DisplayName & vbCrLf & _)
                "  Current path: " & String.Join(" -> ", oPathStack.ConvertAll(Function(p) System.IO.Path.GetFileName(p))) & " -> [" & oCompDef.Document.DisplayName & "] <-- repeats an ancestor above"
            Return False
        End If

        ' --- PERFORMANCE CACHE: if this exact document was already fully
        ' explored earlier this run (from a different branch), reuse that
        ' result instead of re-walking its entire contents again. Safe
        ' because find/replace criteria are fixed for the whole run, so a
        ' document's "does anything inside it need changing" answer can't
        ' change between encounters - only skipped for virtual levels
        ' (bSkipCycleGuardEntry), whose shared identity with their host
        ' would corrupt the cache key.
        If oProcessedResults.ContainsKey(sThisLevelFullName) Then
            Try
                System.IO.File.AppendAllText(sLogFilePath, DateTime.Now.ToString("HH:mm:ss.fff") & "  CACHED (already fully explored this run) - skipping re-traversal: " & oCompDef.Document.DisplayName & vbCrLf)
            Catch
            End Try
            ' CACHE HIT: still repoint any occurrences whose source files were
            ' renamed in a PREVIOUS visit to this same assembly (or by a parent
            ' pass). This handles the same assembly appearing multiple times in
            ' the tree - each instance needs its occurrences repointed even if
            ' the files were already copied/renamed on the first visit.
            Try
                ' Collect ALL matching occurrences FIRST (keyed by old path → list).
                ' FullFileName changes after first Replace(), so we must snapshot
                ' the matches before any Replace() call.
                Dim oCacheGroups As New System.Collections.Generic.Dictionary(Of String, System.Collections.Generic.List(Of ComponentOccurrence))(StringComparer.OrdinalIgnoreCase)
                For Each oCacheOcc As ComponentOccurrence In oCompDef.Occurrences
                    Try
                        Dim sCacheOccPath As String = ""
                        Try : sCacheOccPath = oCacheOcc.Definition.Document.FullFileName : Catch : End Try
                        If sCacheOccPath <> "" AndAlso oRenameMap.ContainsKey(sCacheOccPath) Then
                            If Not oCacheGroups.ContainsKey(sCacheOccPath) Then
                                oCacheGroups(sCacheOccPath) = New System.Collections.Generic.List(Of ComponentOccurrence)
                            End If
                            oCacheGroups(sCacheOccPath).Add(oCacheOcc)
                        End If
                    Catch
                    End Try
                Next
                If oCacheGroups.Count > 0 Then
                    Try
                        Dim oCPAttrs As System.IO.FileAttributes = System.IO.File.GetAttributes(sThisLevelFullName)
                        If (oCPAttrs And System.IO.FileAttributes.ReadOnly) = System.IO.FileAttributes.ReadOnly Then
                            System.IO.File.SetAttributes(sThisLevelFullName, oCPAttrs And Not System.IO.FileAttributes.ReadOnly)
                        End If
                    Catch
                    End Try
                    For Each kvpCG As System.Collections.Generic.KeyValuePair(Of String, System.Collections.Generic.List(Of ComponentOccurrence)) In oCacheGroups
                        Dim sCacheOld As String = kvpCG.Key
                        Dim sCacheNew As String = oRenameMap(sCacheOld)
                        If String.Compare(sCacheOld, sCacheNew, True) = 0 Then Continue For
                        For Each oCacheReplOcc As ComponentOccurrence In kvpCG.Value
                            Try
                                oCacheReplOcc.Replace(sCacheNew, False)
                                Try : oCacheReplOcc.Name = System.IO.Path.GetFileNameWithoutExtension(sCacheNew) : Catch : End Try
                                oLog.Append(vbCrLf & "CACHED REPOINT: " & System.IO.Path.GetFileName(sCacheOld) & "  -->  " & System.IO.Path.GetFileName(sCacheNew) & "  [in " & System.IO.Path.GetFileName(sThisLevelFullName) & "]")
                            Catch exCR As Exception
                                oLog.Append(vbCrLf & "CACHED REPOINT FAILED: " & System.IO.Path.GetFileName(sCacheOld) & " (" & exCR.Message & ")  [in " & System.IO.Path.GetFileName(sThisLevelFullName) & "]")
                            End Try
                        Next
                    Next
                End If
            Catch
            End Try
            Return oProcessedResults(sThisLevelFullName)
        End If

        oVisitedLevels.Add(sThisLevelFullName)
        oPathStack.Add(sThisLevelFullName)
    End If

    Try
        System.IO.File.AppendAllText(sLogFilePath, DateTime.Now.ToString("HH:mm:ss.fff") & "  ENTERING: " & sThisLevelFullName & vbCrLf)
    Catch
    End Try

    ' UNSUPPRESS CYCLE: declared outside Try so Finally can see oSuppressedInLevel.
    Dim oSuppressedInLevel As New System.Collections.Generic.List(Of ComponentOccurrence)
    Dim oScanOcc As ComponentOccurrence
    For Each oScanOcc In oCompDef.Occurrences
        Try
            If oScanOcc.Suppressed Then oSuppressedInLevel.Add(oScanOcc)
        Catch
        End Try
    Next

    If oSuppressedInLevel.Count > 0 Then
        Try
            System.IO.File.AppendAllText(sLogFilePath, DateTime.Now.ToString("HH:mm:ss.fff") & "  Unsuppressing " & oSuppressedInLevel.Count & " occurrence(s) for Mode 1/2 pass." & vbCrLf)
        Catch
        End Try
        For Each oSuppOcc As ComponentOccurrence In oSuppressedInLevel
            Try
                oSuppOcc.Unsuppress()
            Catch exUnsupp As Exception
                Try
                    System.IO.File.AppendAllText(sLogFilePath, DateTime.Now.ToString("HH:mm:ss.fff") & "  WARNING: could not unsuppress " & oSuppOcc.Name & ": " & exUnsupp.Message & vbCrLf)
                Catch
                End Try
            End Try
        Next
    End If

    Try
        ' Snapshot the unique documents referenced at this level first (read-only pass)
        Dim oUniqueDocs As New System.Collections.Generic.Dictionary(Of String, ComponentOccurrence)
        Dim oOcc As ComponentOccurrence

        For Each oOcc In oCompDef.Occurrences
            Dim oRefDoc As Document = Nothing
            Try
                oRefDoc = oOcc.Definition.Document
            Catch
                Continue For ' no document (e.g. virtual component) - skip
            End Try

            Dim sKey As String = oRefDoc.FullFileName
            If Not oUniqueDocs.ContainsKey(sKey) Then
                oUniqueDocs.Add(sKey, oOcc)
            End If
        Next

        For Each oEntry As System.Collections.Generic.KeyValuePair(Of String, ComponentOccurrence) In oUniqueDocs

            Dim sOldFullName As String = oEntry.Key
            Dim oRepOcc As ComponentOccurrence = oEntry.Value
            Dim oRefDoc As Document = oRepOcc.Definition.Document

            Try
                System.IO.File.AppendAllText(sLogFilePath, "    " & DateTime.Now.ToString("HH:mm:ss.fff") & "  checking occurrence: " & oRepOcc.Name & "  ->  " & System.IO.Path.GetFileName(sOldFullName) & vbCrLf)
            Catch
            End Try

            ' --- VIRTUAL COMPONENT: has no independent file - its data
            ' is embedded inside whatever document currently hosts it,
            ' so its FullFileName legitimately matches its immediate
            ' PARENT's file. Never attempt to rename/save it (nothing
            ' separate exists to rename), and NEVER recurse into it -
            ' an earlier version of this rule tried to "look inside" a
            ' virtual assembly to find real nested parts, but that
            ' caused an actual infinite loop in testing: for a virtual
            ' assembly whose identity is shared with the level currently
            ' hosting it, recursing into it can mean re-entering that
            ' SAME level's own occurrence list again - which includes
            ' the same virtual component again, forever. Simply skipping
            ' it is the only safe behaviour here.
            If String.Compare(sOldFullName, sThisLevelFullName, True) = 0 Then
                oLog.Append(vbCrLf & "SKIPPED (virtual component, embedded in parent - no separate file): " & oRepOcc.Name)
                Continue For
            End If

            ' --- SYNTHETIC PATTERN-MEMBER NAME: see IsSyntheticPatternMemberName
            ' for the full explanation. This is NOT a real file - treated the
            ' same as the virtual-component case just above (never renamed,
            ' never recursed into, never used to construct a new file name).
            If IsSyntheticPatternMemberName(sOldFullName) Then
                oLog.Append(vbCrLf & "SKIPPED (synthetic pattern-member name, not a real file): " & oRepOcc.Name & "  [reported as: " & sOldFullName & "]")
                Continue For
            End If

            ' --- EXCLUDED FOLDER, or a genuine Content Center member
            ' regardless of where its file physically lives: skip
            ' entirely, including recursion. This rule previously had no
            ' concept of "leave library/standard parts alone" - it would
            ' happily traverse into and rename standard hardware if the
            ' find text happened to match anywhere in its name.
            ' Project-prefix files always process. Exclusion only when name does NOT match Find.
            Dim sNameForExclude As String = System.IO.Path.GetFileNameWithoutExtension(sOldFullName)
            Dim bNameMatchesFind As Boolean = False
            If bUseContainsMode Then
                bNameMatchesFind = sNameForExclude.ToUpper().Contains(sFind.ToUpper())
            Else
                bNameMatchesFind = sNameForExclude.ToUpper().StartsWith(sFind.ToUpper())
            End If
            If Not bNameMatchesFind Then
                If IsInExcludedFolder(sOldFullName) Then
                    oLog.Append(vbCrLf & "EXCLUDED (vault library/content center/standard folder) - left untouched: " & System.IO.Path.GetFileName(sOldFullName))
                    Continue For
                End If
                If IsContentCenterMember(oRefDoc) Then
                    oLog.Append(vbCrLf & "EXCLUDED (Content Center path) - left untouched: " & System.IO.Path.GetFileName(sOldFullName))
                    Continue For
                End If
            End If

            ' --- OFFICIAL "Non Std Parts" FOLDER: a sub already correctly
            ' relocated by the non-standard-parts mover rule, sitting
            ' directly under THIS assembly's own folder, is left alone -
            ' it's already exactly where it should be. Only the folder
            ' that's a direct sibling of the CURRENT assembly counts as
            ' "official" - a same-named "Non Std Parts" folder belonging
            ' to a different project is NOT exempt, since anything sitting
            ' there genuinely does still need relocating to this one.
            ' MODE 1 ONLY: this exclusion is about avoiding re-shuffling
            ' already-organized subs during a project-prefix CONSOLIDATION
            ' pass. Mode 2 (segment replace) is a targeted text cleanup
            ' tool instead - if you're fixing a specific string in a name,
            ' you clearly want to reach it wherever it lives, including
            ' inside Non Std Parts, so this exclusion doesn't apply there.
            If Not bUseContainsMode AndAlso String.Compare(System.IO.Path.GetDirectoryName(sOldFullName), System.IO.Path.Combine(sTargetFolder, "Non Std Parts"), True) = 0 Then
                oLog.Append(vbCrLf & "EXCLUDED (already in this assembly's official Non Std Parts folder) - left untouched: " & System.IO.Path.GetFileName(sOldFullName))
                Continue For
            End If

            ' --- Already handled elsewhere in the tree this run? ---
            If oRenameMap.ContainsKey(sOldFullName) Then
                Dim sKnownNewName As String = oRenameMap(sOldFullName)
                ' Clear read-only on the PARENT assembly before Replace() -
                ' Vault blocks Replace() on checked-in or File.Copy'd parents.
                Try
                    Dim oParentAttrsRemap As System.IO.FileAttributes = System.IO.File.GetAttributes(oCompDef.Document.FullFileName)
                    If (oParentAttrsRemap And System.IO.FileAttributes.ReadOnly) = System.IO.FileAttributes.ReadOnly Then
                        System.IO.File.SetAttributes(oCompDef.Document.FullFileName, oParentAttrsRemap And Not System.IO.FileAttributes.ReadOnly)
                    End If
                Catch
                End Try
                ' Replace ALL occurrences of this file - not just the representative.
                ' CRITICAL: Collect matching occurrences FIRST before any Replace() call.
                ' After Replace() on the first occurrence, Inventor updates the Document
                ' object's FullFileName for ALL occurrences of that file in the session.
                ' If we check FullFileName inside the replace loop, subsequent occurrences
                ' already show the NEW path and the comparison fails - only one gets fixed.
                ' Collecting first then replacing avoids this entirely.
                Dim oMatchingOccs As New System.Collections.Generic.List(Of ComponentOccurrence)
                For Each oAllOcc As ComponentOccurrence In oCompDef.Occurrences
                    Try
                        Dim sAllOccPath As String = ""
                        Try : sAllOccPath = oAllOcc.Definition.Document.FullFileName : Catch : End Try
                        If String.Compare(sAllOccPath, sOldFullName, True) = 0 Then
                            oMatchingOccs.Add(oAllOcc)
                        End If
                    Catch
                    End Try
                Next
                Dim iRemapCount As Integer = 0
                For Each oMatchOcc As ComponentOccurrence In oMatchingOccs
                    Try
                        oMatchOcc.Replace(sKnownNewName, False)
                        Try : oMatchOcc.Name = System.IO.Path.GetFileNameWithoutExtension(sKnownNewName) : Catch : End Try
                        iRemapCount = iRemapCount + 1
                        bChangedHere = True
                    Catch exAllRep As Exception
                        oLog.Append(vbCrLf & "FAILED to re-point occurrence of " & System.IO.Path.GetFileName(sKnownNewName) & " (" & exAllRep.Message & ")")
                    End Try
                Next
                If iRemapCount > 0 Then
                    oLog.Append(vbCrLf & "Re-pointed " & iRemapCount & " occurrence(s) to already-renamed file: " & System.IO.Path.GetFileName(sKnownNewName))
                End If
                Continue For ' fully handled - skip recursion/SaveAs below for this entry
            End If

            ' FIX B: Inventor updates FullFileName in session after Replace().
            ' If a PART already starts with sReplace it was already renamed -
            ' nothing more to do. ASSEMBLIES must NOT be skipped even if their
            ' own name starts with sReplace - their CHILDREN may still have old
            ' PJ174 names that need processing via recursion.
            If Not bUseContainsMode AndAlso _
               oRefDoc.DocumentType = kPartDocumentObject AndAlso _
               System.IO.Path.GetFileNameWithoutExtension(sOldFullName).ToUpper().StartsWith(sReplace.ToUpper()) Then
                Continue For  ' part already correctly named - skip
            End If

            ' --- TOP-DOWN for assemblies: SaveAs the assembly FIRST if it
            ' matches the Find prefix, then recurse into the NEW COPY rather
            ' than the original. This ensures:
            ' 1. The assembly copy exists on disk before its children are
            '    processed - if Inventor crashes mid-child the parent copy
            '    is already there for the next run.
            ' 2. Replace() is called on the local copy's occurrences, not
            '    the original checked-in Vault assembly - avoiding E_FAIL.
            ' For assemblies that DON'T match (already renamed), recurse
            ' into them as before (bottom-up is fine, they're already local).
            Dim bChildChanged As Boolean = False
            Dim sOldFileName As String = System.IO.Path.GetFileNameWithoutExtension(sOldFullName)
            Dim sExt As String = System.IO.Path.GetExtension(sOldFullName)
            Dim bDidRename As Boolean = False

            ' Mode 1: STARTS WITH. Mode 2: CONTAINS.
            Dim bIsMatch As Boolean
            If bUseContainsMode Then
                bIsMatch = sOldFileName.ToUpper().Contains(sFind.ToUpper())
            Else
                bIsMatch = sOldFileName.ToUpper().StartsWith(sFind.ToUpper())
            End If

            ' CROSS-BATCH FALLBACK: In Mode 4, a parent assembly can belong to
            ' one prefix (e.g. PJ174-) while some of its direct children use a
            ' different prefix (e.g. PJ00174-). The child's prefix is deferred
            ' to its own batch pass, but by then its parent is already open and
            ' the deferred pass never re-enters this parent. Result: those children
            ' are silently skipped by both passes.
            ' Fix: when bIsMatch=False for a PART and we have other batch tokens,
            ' check if the part matches any other token and process it right here
            ' using that token's find/replace, before moving on.
            If Not bIsMatch AndAlso _
               oRefDoc.DocumentType = kPartDocumentObject AndAlso _
               oBatchAllFinds IsNot Nothing AndAlso oBatchAllFinds.Count > 0 AndAlso _
               sAllReplace <> "" Then
                For Each sOtherFind As String In oBatchAllFinds
                    If String.Compare(sOtherFind, sFind, True) = 0 Then Continue For  ' same token - already failed
                    Dim bOtherMatch As Boolean
                    If bUseContainsMode Then
                        bOtherMatch = sOldFileName.ToUpper().Contains(sOtherFind.ToUpper())
                    Else
                        bOtherMatch = sOldFileName.ToUpper().StartsWith(sOtherFind.ToUpper())
                    End If
                    If bOtherMatch Then
                        ' Process this part now using the matching token's find/replace
                        Dim sXNewFileName As String = sAllReplace & sOldFileName.Substring(sOtherFind.Length)
                        Dim sXNewFullName As String = System.IO.Path.Combine(sTargetFolder, sXNewFileName & sExt)
                        If Not oRenameMap.ContainsKey(sOldFullName) Then
                            If Not System.IO.File.Exists(sXNewFullName) Then
                                Try
                                    System.IO.File.Copy(sOldFullName, sXNewFullName, True)
                                    Try
                                        Dim oXA As System.IO.FileAttributes = System.IO.File.GetAttributes(sXNewFullName)
                                        If (oXA And System.IO.FileAttributes.ReadOnly) = System.IO.FileAttributes.ReadOnly Then
                                            System.IO.File.SetAttributes(sXNewFullName, oXA And Not System.IO.FileAttributes.ReadOnly)
                                        End If
                                    Catch
                                    End Try
                                    oLog.Append(vbCrLf & sOldFileName & sExt & "   -->   " & sXNewFileName & sExt & "  [cross-batch: " & sOtherFind & " -> " & sAllReplace & "]")
                                Catch exXCopy As Exception
                                    oLog.Append(vbCrLf & "FAILED (cross-batch copy): " & sOldFileName & sExt & " (" & exXCopy.Message & ")")
                                    Exit For
                                End Try
                            End If
                            oRenameMap(sOldFullName) = sXNewFullName
                            iCount = iCount + 1
                        End If
                        ' Repoint the occurrence regardless (copy may have been from prior run)
                        If System.IO.File.Exists(sXNewFullName) Then
                            Try
                                oRepOcc.Replace(sXNewFullName, False)
                                Try : oRepOcc.Name = sXNewFileName : Catch : End Try
                                bChangedHere = True
                                bDidRename = True
                            Catch exXRep As Exception
                                ' FD fallback
                                Try
                                    Dim oXFD As FileDescriptor = oRepOcc.ReferencedFileDescriptor
                                    If oXFD IsNot Nothing Then
                                        oXFD.ReplaceReference(sXNewFullName)
                                        bChangedHere = True
                                        bDidRename = True
                                    End If
                                Catch
                                End Try
                            End Try
                        End If
                        Exit For
                    End If
                Next
            End If

            If oRefDoc.DocumentType = kAssemblyDocumentObject AndAlso bIsMatch Then
                ' FRAME GENERATOR package? (broad detection: FRAME/-F name, SKEL, Frame folder, AS members)
                If Not bUseContainsMode AndAlso IsFrameGeneratorAssembly(oRefDoc.ComponentDefinition, sOldFullName) Then
                    Try
                        Dim bFgChanged As Boolean = ProcessFrameGeneratorSet( _
                            oRefDoc, oRepOcc, sFind, sReplace, bUseContainsMode, _
                            sTargetFolder, sTopAssemblyFullName, oLog, iCount, oRenameMap, sLogFilePath, oBatchAllFinds, sAllReplace)
                        If bFgChanged Then
                            bChangedHere = True
                            bDidRename = True
                        End If
                    Catch exFg As Exception
                        oLog.Append(vbCrLf & "FAILED Frame Generator set processing: " & sOldFileName & sExt & " (" & exFg.Message & ")")
                    End Try
                    GoTo NextOccurrence
                End If

                ' TOP-DOWN path for matching assemblies:
                ' 1. Compute new name and SaveAs (or File.Copy) the assembly
                ' 2. Open the new copy
                ' 3. Recurse into the NEW COPY's children
                ' 4. Replace the occurrence in the current parent
                Dim sNewFileName As String
                If bUseContainsMode Then
                    sNewFileName = Trim(ReplaceAllCaseInsensitive(sOldFileName, sFind, sReplace)).Replace("_ ", "_").Replace("  ", " ")
                Else
                    sNewFileName = Trim(sReplace & sOldFileName.Substring(sFind.Length)).Replace("_ ", "_").Replace("  ", " ")
                End If

                Dim sEffectiveTargetFolder As String = GetEffectiveTargetFolder(sOldFullName, sTargetFolder)
                Dim bRoutedToNonStd As Boolean = (String.Compare(sEffectiveTargetFolder, sTargetFolder, True) <> 0)
                Dim sNewFullName As String = System.IO.Path.Combine(sEffectiveTargetFolder, sNewFileName & sExt)

                ' Safety check
                If String.Compare(sNewFullName, sTopAssemblyFullName, True) = 0 Then
                    oLog.Append(vbCrLf & "SAFETY SKIP: computed new name for '" & sOldFileName & sExt & "' matches the TOP ASSEMBLY'S OWN FILE - refusing to repoint.")
                    GoTo NextOccurrence
                End If

                ' Check if copy already exists from a previous run
                If Not System.IO.File.Exists(sNewFullName) Then
                    ' SaveAs the assembly to the new name
                    Try
                        System.IO.File.AppendAllText(sLogFilePath, "      " & DateTime.Now.ToString("HH:mm:ss.fff") & "  SaveAs starting: " & sOldFileName & sExt & "  ->  " & sNewFileName & sExt & vbCrLf)
                    Catch
                    End Try
                    Dim bAsmSaveAsOk As Boolean = False
                    Try
                        oRefDoc.SaveAs(sNewFullName, True)
                        bAsmSaveAsOk = True
                        Try
                            System.IO.File.AppendAllText(sLogFilePath, "      " & DateTime.Now.ToString("HH:mm:ss.fff") & "  SaveAs finished." & vbCrLf)
                        Catch
                        End Try
                    Catch exSaveAs As Exception
                        Try
                            System.IO.File.AppendAllText(sLogFilePath, "      " & DateTime.Now.ToString("HH:mm:ss.fff") & "  SaveAs threw (" & exSaveAs.Message & ") - will attempt File.Copy fallback." & vbCrLf)
                        Catch
                        End Try
                    End Try
                    If Not bAsmSaveAsOk OrElse Not System.IO.File.Exists(sNewFullName) Then
                        Try
                            System.IO.File.Copy(sOldFullName, sNewFullName, False)
                            Try
                                System.IO.File.AppendAllText(sLogFilePath, "      " & DateTime.Now.ToString("HH:mm:ss.fff") & "  File.Copy fallback succeeded." & vbCrLf)
                            Catch
                            End Try
                        Catch exCopy As Exception
                            oLog.Append(vbCrLf & "FAILED: " & sOldFileName & sExt & " (SaveAs and File.Copy both failed: " & exCopy.Message & ")")
                            GoTo NextOccurrence
                        End Try
                    End If
                End If

                ' CRITICAL SAFETY ORDER:
                ' 1. Copy assembly to target folder
                ' 2. Replace() occurrence in parent → confirms parent is updated
                ' 3. ONLY IF Replace succeeded, open copy and recurse into children
                '
                ' This ensures we NEVER modify the contents of a sub-assembly
                ' until it has been successfully copied AND repointed in its parent.
                ' If Replace() fails, children stay completely untouched.

                ' Step 1: Repoint the occurrence in the CURRENT parent to the new copy
                oRenameMap(sOldFullName) = sNewFullName
                iCount = iCount + 1

                ' Clear read-only on CURRENT parent before Replace
                Try
                    Dim oParentAttrs As System.IO.FileAttributes = System.IO.File.GetAttributes(oCompDef.Document.FullFileName)
                    If (oParentAttrs And System.IO.FileAttributes.ReadOnly) = System.IO.FileAttributes.ReadOnly Then
                        System.IO.File.SetAttributes(oCompDef.Document.FullFileName, oParentAttrs And Not System.IO.FileAttributes.ReadOnly)
                    End If
                Catch
                End Try

                Dim bAsmReplaceOk As Boolean = False
                Try
                    oRepOcc.Replace(sNewFullName, False)
                    bAsmReplaceOk = True
                    Try
                        oRepOcc.Name = System.IO.Path.GetFileNameWithoutExtension(sNewFullName)
                    Catch
                    End Try
                Catch exReplace As Exception
                    oLog.Append(vbCrLf & "FAILED to repoint assembly occurrence: " & sOldFileName & sExt & " (" & exReplace.Message & ") - parent: " & System.IO.Path.GetFileName(oCompDef.Document.FullFileName) & " - children NOT processed (original untouched)")
                End Try

                ' Cleanup old copy if in same folder
                If String.Compare(System.IO.Path.GetDirectoryName(sOldFullName), _
                                  System.IO.Path.GetDirectoryName(sNewFullName), True) = 0 AndAlso _
                   String.Compare(sOldFullName, sNewFullName, True) <> 0 AndAlso _
                   Not IsInExcludedFolder(sOldFullName) AndAlso _
                   System.IO.File.Exists(sOldFullName) Then
                    Try
                        System.IO.File.Delete(sOldFullName)
                        oLog.Append(vbCrLf & "  CLEANUP: deleted old assembly copy: " & sOldFileName & sExt)
                    Catch exDel As Exception
                        oLog.Append(vbCrLf & "  CLEANUP WARNING: could not delete: " & sOldFileName & sExt & " (" & exDel.Message & ")")
                    End Try
                End If

                If bAsmReplaceOk Then
                    oLog.Append(vbCrLf & sOldFileName & sExt & "   -->   " & sNewFileName & sExt & IIf(bRoutedToNonStd, "  (routed to Non Std Parts)", ""))
                    bChangedHere = True
                    bDidRename = True

                    ' Step 2: ONLY NOW open the new copy and recurse into its children.
                    ' Replace() confirmed the parent is correctly updated - safe to proceed.
                    Dim bNewAsmOpenedHere As Boolean = False
                    Dim oNewAsmDoc As Document = OpenDocTracked(sNewFullName, bNewAsmOpenedHere)
                    If oNewAsmDoc Is Nothing Then
                        oLog.Append(vbCrLf & "WARNING: could not open new assembly copy for child processing: " & sNewFileName & sExt)
                    Else
                        ' Clear read-only on the new copy before recursing
                        Try
                            Dim oNewAttrs As System.IO.FileAttributes = System.IO.File.GetAttributes(sNewFullName)
                            If (oNewAttrs And System.IO.FileAttributes.ReadOnly) = System.IO.FileAttributes.ReadOnly Then
                                System.IO.File.SetAttributes(sNewFullName, oNewAttrs And Not System.IO.FileAttributes.ReadOnly)
                            End If
                        Catch
                        End Try
                        ' FIX 1 - CACHE EVICTION: the new copy's path may already be in
                        ' oProcessedResults from when it was first explored as the original
                        ' unmodified file (False = nothing changed). That cached result
                        ' causes ProcessLevel to return immediately, leaving all the new
                        ' copy's children unprocessed - this is what produces "CYCLE
                        ' DETECTED / refusing to re-enter" on renamed subs like
                        ' Support_Frame and HRAIL. Evicting the entry forces a fresh walk.
                        If oProcessedResults.ContainsKey(sNewFullName) Then
                            oProcessedResults.Remove(sNewFullName)
                        End If
                        ' Recurse into the NEW COPY's children
                        Try
                            bChildChanged = ProcessLevel(oNewAsmDoc.ComponentDefinition, sFind, sReplace, bUseContainsMode, sTargetFolder, sTopAssemblyFullName, oLog, iCount, oRenameMap, oSavedInPlace, oVisitedLevels, oPathStack, oProcessedResults, sLogFilePath, , oNeedsCheckout, oBatchAllFinds, sAllReplace)
                        Catch ex As Exception
                            oLog.Append(vbCrLf & "FAILED traversing new assembly copy: " & sNewFileName & sExt & " (" & ex.Message & ")")
                        End Try
                        ' Free memory: close if we opened it and it is no longer needed
                        CloseIfOpenedHere(oNewAsmDoc, bNewAsmOpenedHere)
                        oNewAsmDoc = Nothing
                    End If
                End If
                GoTo NextOccurrence

            ElseIf oRefDoc.DocumentType = kAssemblyDocumentObject Then
                ' Assembly that does NOT match Find prefix.
                '
                ' BOLTED CONNECTION (Design Accelerator) CHECK:
                ' If this is a DA Bolted Connection assembly, its fastener occurrences
                ' are DA-managed and cannot be replaced via ComponentOccurrence.Replace().
                ' Use ProcessBoltedConnectionRefs() which works at file descriptor level.
                If IsBoltedConnectionAssembly(oRefDoc.ComponentDefinition) AndAlso _
                   IsDocSafeToMutate(sOldFullName, sTargetFolder, sTopAssemblyFullName) Then
                    Try
                        If ProcessBoltedConnectionRefs(oRefDoc, sFind, sReplace, bUseContainsMode, sTargetFolder, oLog, iCount, oRenameMap) Then
                            bChildChanged = True
                            ' Save the bolted connection assembly after repointing
                            Try
                                Dim oBCAttrs As System.IO.FileAttributes = System.IO.File.GetAttributes(sOldFullName)
                                If (oBCAttrs And System.IO.FileAttributes.ReadOnly) = System.IO.FileAttributes.ReadOnly Then
                                    System.IO.File.SetAttributes(sOldFullName, oBCAttrs And Not System.IO.FileAttributes.ReadOnly)
                                End If
                            Catch
                            End Try
                            Try : oRefDoc.Save2(False) : Catch exBCSave As Exception
                                oLog.Append(vbCrLf & "  BOLTED-CONN save FAILED: " & sOldFileName & sExt & " (" & exBCSave.Message & ")")
                            End Try
                        End If
                    Catch exBC As Exception
                        oLog.Append(vbCrLf & "FAILED processing bolted connection refs: " & sOldFileName & sExt & " (" & exBC.Message & ")")
                    End Try
                    GoTo NextOccurrence  ' fully handled by dedicated BC processor
                End If

                ' If already in the target folder - recurse directly (safe to mutate).
                ' If outside the target folder (Vault-managed original) - make a
                ' same-name local copy first, recurse into the COPY, save the copy.
                ' We do NOT call oRepOcc.Replace() on the original parent to repoint
                ' to the copy - that parent is Vault-managed and Replace() always
                ' throws E_FAIL there. The copy is found via the project search path.
                Dim oWorkDoc As Document = oRefDoc
                Dim sWorkFull As String = sOldFullName
                Dim bWorkOpenedHere As Boolean = False

                ' BATCH-PASS GUARD:
                '  - If this file matches a DIFFERENT batch find token, defer
                '    entirely (that pass will rename it). Do NOT recurse here.
                '  - If this file already starts with the REPLACE token (e.g.
                '    PJ00999-... during a PJ174 pass), do NOT rename the parent,
                '    but DO still recurse into assemblies so nested children
                '    that still match the current Find (e.g. PJ174-16-075 under
                '    PJ00999-19-000 / PJ00999-22-000) are found and fixed.
                Dim bWillBeHandledByOtherPass As Boolean = False
                Dim bAlreadyCorrectPrefix As Boolean = False
                If oBatchAllFinds IsNot Nothing AndAlso oBatchAllFinds.Count > 0 Then
                    Dim sOldFileNameOnly As String = System.IO.Path.GetFileNameWithoutExtension(sOldFullName)
                    If sAllReplace <> "" AndAlso sOldFileNameOnly.ToUpper().StartsWith(sAllReplace.ToUpper()) Then
                        bAlreadyCorrectPrefix = True
                    End If
                    If Not bAlreadyCorrectPrefix Then
                        For Each sOtherFind As String In oBatchAllFinds
                            If String.Compare(sOtherFind, sFind, True) <> 0 AndAlso _
                               sOldFileNameOnly.ToUpper().StartsWith(sOtherFind.ToUpper()) Then
                                bWillBeHandledByOtherPass = True
                                oLog.Append(vbCrLf & "DEFERRED (handled by batch pass '" & sOtherFind & "'): " & sOldFileName & sExt)
                                Exit For
                            End If
                        Next
                    End If
                End If
                If bWillBeHandledByOtherPass Then GoTo NextOccurrence

                ' Already-correct parent (name starts with new PJ): recurse only
                If bAlreadyCorrectPrefix Then
                    ' FRAME GENERATOR: if this already-correct assembly is a FG package,
                    ' call ProcessFrameGeneratorSet to repoint its children. On re-runs
                    ' the FRAME assembly exists on disk but its children may still point
                    ' to Centerra if the first run failed FG detection (e.g. -F_ReferenceCopy
                    ' naming). This catches that case without needing a fresh run.
                    If sExt.ToUpper() = ".IAM" AndAlso Not bUseContainsMode AndAlso _
                       IsDocSafeToMutate(sOldFullName, sTargetFolder, sTopAssemblyFullName) AndAlso _
                       IsFrameGeneratorAssembly(oRefDoc.ComponentDefinition, sOldFullName) Then
                        Try
                            Dim bFgChangedAC As Boolean = ProcessFrameGeneratorSet( _
                                oRefDoc, oRepOcc, sFind, sReplace, bUseContainsMode, _
                                sTargetFolder, sTopAssemblyFullName, oLog, iCount, oRenameMap, sLogFilePath, oBatchAllFinds, sAllReplace)
                            If bFgChangedAC Then bChangedHere = True
                        Catch exFgAC As Exception
                            oLog.Append(vbCrLf & "FAILED Frame Generator set processing (already-correct): " & sOldFileName & sExt & " (" & exFgAC.Message & ")")
                        End Try
                        GoTo NextOccurrence
                    End If
                    If sExt.ToUpper() = ".IAM" AndAlso IsDocSafeToMutate(sOldFullName, sTargetFolder, sTopAssemblyFullName) Then
                        Dim bChildChangedAC As Boolean = False
                        Try
                            If oProcessedResults.ContainsKey(sOldFullName) Then oProcessedResults.Remove(sOldFullName)
                            ' Also evict any renamed version of this assembly from the cache.
                            ' When the PJ174 pass renames V01-17-000 and then the PJ00145 pass
                            ' later sees PJ00999-V01-17-000 as already-correct, the cache may
                            ' already contain the PJ00999 path from an earlier branch visit,
                            ' causing ProcessLevel to skip its children (including V01-75-000).
                            For Each kvpAC As System.Collections.Generic.KeyValuePair(Of String, String) In oRenameMap
                                If String.Compare(kvpAC.Value, sOldFullName, True) = 0 AndAlso _
                                   oProcessedResults.ContainsKey(kvpAC.Key) Then
                                    oProcessedResults.Remove(kvpAC.Key)
                                End If
                            Next
                            bChildChangedAC = ProcessLevel(oRefDoc.ComponentDefinition, sFind, sReplace, bUseContainsMode, sTargetFolder, sTopAssemblyFullName, oLog, iCount, oRenameMap, oSavedInPlace, oVisitedLevels, oPathStack, oProcessedResults, sLogFilePath, , oNeedsCheckout, oBatchAllFinds, sAllReplace)
                        Catch exAC As Exception
                            oLog.Append(vbCrLf & "FAILED traversing already-correct sub-assembly: " & sOldFileName & sExt & " (" & exAC.Message & ")")
                        End Try
                        Try
                            If IsBoltedConnectionAssembly(oRefDoc.ComponentDefinition) Then
                                If ProcessBoltedConnectionRefs(oRefDoc, sFind, sReplace, bUseContainsMode, sTargetFolder, oLog, iCount, oRenameMap) Then
                                    bChildChangedAC = True
                                End If
                            End If
                        Catch
                        End Try
                        Try
                            If UpdateLinkedParamsAfterRename(oRefDoc, oRenameMap, oLog, iCount, sFind, sReplace, bUseContainsMode, sTargetFolder, oNeedsCheckout) Then
                                bChildChangedAC = True
                            End If
                        Catch
                        End Try
                        If bChildChangedAC Then
                            bChangedHere = True
                            Try
                                Dim oAcAttrs2 As System.IO.FileAttributes = System.IO.File.GetAttributes(sOldFullName)
                                If (oAcAttrs2 And System.IO.FileAttributes.ReadOnly) = System.IO.FileAttributes.ReadOnly Then
                                    System.IO.File.SetAttributes(sOldFullName, oAcAttrs2 And Not System.IO.FileAttributes.ReadOnly)
                                End If
                            Catch
                            End Try
                            Try
                                oRefDoc.Update()
                                oRefDoc.Save2(False)
                                oSavedInPlace.Add(sOldFullName)
                                oLog.Append(vbCrLf & "  Saved already-correct sub-assembly after child updates: " & sOldFileName & sExt)
                            Catch exAcSav2 As Exception
                                oLog.Append(vbCrLf & "  FAILED saving already-correct sub-assembly '" & sOldFileName & sExt & "': " & exAcSav2.Message & " (check out in Vault and re-run)")
                                If oNeedsCheckout IsNot Nothing Then oNeedsCheckout.Add(sOldFullName)
                            End Try
                        End If
                    End If
                    GoTo NextOccurrence
                End If

                If Not IsDocSafeToMutate(sOldFullName, sTargetFolder, sTopAssemblyFullName) Then
                    Dim sLocFolder As String = GetEffectiveTargetFolder(sOldFullName, sTargetFolder)
                    Dim sLocFull As String = System.IO.Path.Combine(sLocFolder, sOldFileName & sExt)

                    If String.Compare(sLocFull, sTopAssemblyFullName, True) = 0 Then
                        oLog.Append(vbCrLf & "SAFETY SKIP: localizing '" & sOldFileName & sExt & "' would collide with top assembly.")
                        GoTo NextOccurrence
                    End If

                    If oRenameMap.ContainsKey(sOldFullName) Then
                        sLocFull = oRenameMap(sOldFullName)
                    ElseIf Not System.IO.File.Exists(sLocFull) Then
                        Dim bLocOk As Boolean = False
                        Try
                            If Not System.IO.Directory.Exists(sLocFolder) Then System.IO.Directory.CreateDirectory(sLocFolder)
                        Catch
                        End Try
                        Try
                            System.IO.File.AppendAllText(sLogFilePath, "      " & DateTime.Now.ToString("HH:mm:ss.fff") & "  LOCALIZE (non-matching parent) SaveAs/Copy: " & sOldFileName & sExt & vbCrLf)
                        Catch
                        End Try
                        Try
                            oRefDoc.SaveAs(sLocFull, True)
                            bLocOk = System.IO.File.Exists(sLocFull)
                        Catch
                            Try
                                System.IO.File.Copy(sOldFullName, sLocFull, False)
                                bLocOk = System.IO.File.Exists(sLocFull)
                            Catch exLoc As Exception
                                oLog.Append(vbCrLf & "FAILED to localize non-matching parent: " & sOldFileName & sExt & " (" & exLoc.Message & ")")
                            End Try
                        End Try
                        If bLocOk Then
                            Try
                                Dim oLocAttrs As System.IO.FileAttributes = System.IO.File.GetAttributes(sLocFull)
                                If (oLocAttrs And System.IO.FileAttributes.ReadOnly) = System.IO.FileAttributes.ReadOnly Then
                                    System.IO.File.SetAttributes(sLocFull, oLocAttrs And Not System.IO.FileAttributes.ReadOnly)
                                End If
                            Catch
                            End Try
                            oRenameMap(sOldFullName) = sLocFull
                            oLog.Append(vbCrLf & "LOCALIZED (same name, local copy made): " & sOldFileName & sExt & "  -->  " & sLocFull)
                        Else
                            oLog.Append(vbCrLf & "LOCALIZE FAILED - skipping children of: " & sOldFileName & sExt)
                            GoTo NextOccurrence
                        End If
                    Else
                        oRenameMap(sOldFullName) = sLocFull
                        oLog.Append(vbCrLf & "LOCALIZED (already existed in target): " & sOldFileName & sExt)
                    End If

                    ' Open the local copy to recurse into
                    Try
                        oWorkDoc = OpenDocTracked(sLocFull, bWorkOpenedHere)
                        sWorkFull = sLocFull
                        If oWorkDoc Is Nothing Then
                            oLog.Append(vbCrLf & "FAILED opening local copy for child processing: " & sOldFileName & sExt)
                            GoTo NextOccurrence
                        End If
                    Catch exLocOpen As Exception
                        oLog.Append(vbCrLf & "FAILED opening local copy for child processing: " & sOldFileName & sExt & " (" & exLocOpen.Message & ")")
                        GoTo NextOccurrence
                    End Try
                End If

                ' Recurse into oWorkDoc (local copy or original if already local)
                If oWorkDoc IsNot Nothing Then
                    If oProcessedResults.ContainsKey(sWorkFull) Then oProcessedResults.Remove(sWorkFull)
                    Try
                        bChildChanged = ProcessLevel(oWorkDoc.ComponentDefinition, sFind, sReplace, bUseContainsMode, sTargetFolder, sTopAssemblyFullName, oLog, iCount, oRenameMap, oSavedInPlace, oVisitedLevels, oPathStack, oProcessedResults, sLogFilePath, , oNeedsCheckout, oBatchAllFinds, sAllReplace)
                    Catch ex As Exception
                        oLog.Append(vbCrLf & "FAILED traversing sub-assembly: " & sOldFileName & sExt & " (" & ex.Message & ")")
                    End Try
                    Try
                        If UpdateLinkedParamsAfterRename(oWorkDoc, oRenameMap, oLog, iCount, sFind, sReplace, bUseContainsMode, sTargetFolder, oNeedsCheckout) Then
                            bChildChanged = True
                        End If
                    Catch ex As Exception
                        oLog.Append(vbCrLf & "FAILED updating param table links in asm: " & sOldFileName & sExt & " (" & ex.Message & ")")
                    End Try
                    ' Save the local copy if its children changed (never the original)
                    If bChildChanged AndAlso String.Compare(sWorkFull, sOldFullName, True) <> 0 Then
                        Try
                            If oWorkDoc.Dirty Then oWorkDoc.Save2(False)
                            oSavedInPlace.Add(sWorkFull)
                            oLog.Append(vbCrLf & "  Saved local copy after child updates: " & sOldFileName & sExt)
                        Catch exSav As Exception
                            oLog.Append(vbCrLf & "  FAILED saving local copy: " & sOldFileName & sExt & " (" & exSav.Message & ")")
                        End Try
                    End If
                    CloseIfOpenedHere(oWorkDoc, bWorkOpenedHere)
                    If bWorkOpenedHere Then oWorkDoc = Nothing
                End If
            ElseIf oRefDoc.DocumentType = kPartDocumentObject Then
                ' SAFETY GUARD: only run derive source and param table fixes on
                ' parts that are already in the target folder (local copies).
                ' Parts still in the original Vault folder must not have their
                ' internal references modified - ReplaceReference on an original
                ' Vault file modifies it on disk, contaminating the source project.
                ' Parts not yet local will be SaveAs'd to the target folder when
                ' their own prefix is processed; the post-traversal
                ' RunDerivedAndParamFixPass then fixes their derive sources and
                ' param links on the local copy.
                ' Exception: if the part is already in oRenameMap it was SaveAs'd
                ' this run - use the renamed (local) path for the safety check.
                Dim sPartCheckPath As String = oRefDoc.FullFileName
                If oRenameMap.ContainsKey(sPartCheckPath) Then sPartCheckPath = oRenameMap(sPartCheckPath)
                Dim bPartIsLocalNow As Boolean = IsDocSafeToMutate(sPartCheckPath, sTargetFolder, sTopAssemblyFullName)
                If bPartIsLocalNow Then
                    ' Part is local - safe to fix its derive sources and param links
                    Dim oWorkPart As Document = oRefDoc
                    Dim bWorkPartOpenedHere As Boolean = False
                    If oRenameMap.ContainsKey(oRefDoc.FullFileName) Then
                        ' Use the renamed local copy for modifications
                        Dim sLocalPath As String = oRenameMap(oRefDoc.FullFileName)
                        Try
                            Try : oWorkPart = ThisApplication.Documents.ItemByName(sLocalPath) : Catch : oWorkPart = Nothing : End Try
                            If oWorkPart Is Nothing Then oWorkPart = OpenDocTracked(sLocalPath, bWorkPartOpenedHere)
                            If oWorkPart Is Nothing Then oWorkPart = oRefDoc  ' fall back to original if open fails
                        Catch
                            oWorkPart = oRefDoc  ' fall back to original if open fails
                            bWorkPartOpenedHere = False
                        End Try
                    End If
                    Try
                        If ProcessDerivedSource(oWorkPart, sFind, sReplace, bUseContainsMode, sTargetFolder, sTopAssemblyFullName, oLog, iCount, oRenameMap, sLogFilePath) Then
                            bChildChanged = True
                        End If
                    Catch ex As Exception
                        oLog.Append(vbCrLf & "FAILED checking derived source in: " & oWorkPart.DisplayName & " (" & ex.Message & ")")
                    End Try
                    Try
                        If UpdateLinkedParamsAfterRename(oWorkPart, oRenameMap, oLog, iCount, sFind, sReplace, bUseContainsMode, sTargetFolder, oNeedsCheckout) Then
                            bChildChanged = True
                        End If
                    Catch ex As Exception
                        oLog.Append(vbCrLf & "FAILED updating param table links in: " & oWorkPart.DisplayName & " (" & ex.Message & ")")
                    End Try
                    ' Close the local copy only if we opened it here and it has no unsaved edits
                    CloseIfOpenedHere(oWorkPart, bWorkPartOpenedHere)
                End If  ' bPartIsLocalNow
            End If

            If bIsMatch Then

                Dim sNewFileName As String
                If bUseContainsMode Then
                    sNewFileName = Trim(ReplaceAllCaseInsensitive(sOldFileName, sFind, sReplace)).Replace("_ ", "_").Replace("  ", " ")
                Else
                    sNewFileName = Trim(sReplace & sOldFileName.Substring(sFind.Length)).Replace("_ ", "_").Replace("  ", " ")
                End If

                ' Route to THIS assembly's own "Non Std Parts" folder if
                ' the sub currently lives in a folder named that (from any
                ' project) - otherwise the main assembly folder as usual.
                Dim sEffectiveTargetFolder As String = GetEffectiveTargetFolder(sOldFullName, sTargetFolder)
                Dim bRoutedToNonStd As Boolean = (String.Compare(sEffectiveTargetFolder, sTargetFolder, True) <> 0)
                Dim sNewFullName As String = System.IO.Path.Combine(sEffectiveTargetFolder, sNewFileName & sExt)

                ' True when the file NAME doesn't actually change and only
                ' the FOLDER differs (e.g. Find and Replace entered
                ' identically, on purpose) - see LOCALIZE WITHOUT RENAMING
                ' in the header comment. Used below purely to make the log
                ' clearer about what actually happened.
                Dim bLocalizeOnly As Boolean = (String.Compare(sNewFileName, sOldFileName, True) = 0) AndAlso (String.Compare(System.IO.Path.GetDirectoryName(sOldFullName), sEffectiveTargetFolder, True) <> 0)

                ' --- SAFETY: never rename/repoint to the TOP ASSEMBLY'S
                ' OWN FILE. Every renamed file lands in the same top-
                ' folder, so a sub's computed new name CAN coincidentally
                ' collide with the top assembly's own current name -
                ' repointing to it would silently create a circular
                ' reference. Skip and flag it loudly instead.
                If String.Compare(sNewFullName, sTopAssemblyFullName, True) = 0 Then
                    oLog.Append(vbCrLf & "SAFETY SKIP: computed new name for '" & sOldFileName & sExt & "' matches the TOP ASSEMBLY'S OWN FILE (" & System.IO.Path.GetFileName(sTopAssemblyFullName) & ") - refusing to repoint (would create a circular reference). Left unchanged - check this one manually.")
                ElseIf System.IO.File.Exists(sNewFullName) Then
                    ' Clear read-only on the PARENT assembly before Replace() -
                    ' Vault blocks Replace() on checked-in or File.Copy'd parents.
                    Dim sParentFullForReplace As String = ""
                    Try : sParentFullForReplace = oCompDef.Document.FullFileName : Catch : End Try
                    Try
                        If sParentFullForReplace <> "" Then
                            Dim oParentAttrsExist As System.IO.FileAttributes = System.IO.File.GetAttributes(sParentFullForReplace)
                            If (oParentAttrsExist And System.IO.FileAttributes.ReadOnly) = System.IO.FileAttributes.ReadOnly Then
                                System.IO.File.SetAttributes(sParentFullForReplace, oParentAttrsExist And Not System.IO.FileAttributes.ReadOnly)
                            End If
                        End If
                    Catch
                    End Try
                    Dim bReplaceOk As Boolean = False
                    Dim sReplaceFailMsg As String = ""
                    ' Attempt 1: normal occurrence Replace
                    Try
                        oRepOcc.Replace(sNewFullName, False)
                        Try : oRepOcc.Name = System.IO.Path.GetFileNameWithoutExtension(sNewFullName) : Catch : End Try
                        bReplaceOk = True
                    Catch exReplace As Exception
                        sReplaceFailMsg = "Replace: " & exReplace.Message
                    End Try
                    ' Attempt 2: occurrence's own ReferencedFileDescriptor
                    If Not bReplaceOk Then
                        Try
                            Dim oOccFD As FileDescriptor = Nothing
                            Try : oOccFD = oRepOcc.ReferencedFileDescriptor : Catch : oOccFD = Nothing : End Try
                            If oOccFD IsNot Nothing Then
                                oOccFD.ReplaceReference(sNewFullName)
                                Try : oRepOcc.Name = System.IO.Path.GetFileNameWithoutExtension(sNewFullName) : Catch : End Try
                                bReplaceOk = True
                                oLog.Append(vbCrLf & "  OCC-FD REPOINT: " & sOldFileName & sExt & "  -->  " & sNewFileName & sExt & "  [in " & System.IO.Path.GetFileName(sParentFullForReplace) & "]")
                            End If
                        Catch exOccFD As Exception
                            sReplaceFailMsg = sReplaceFailMsg & "; OccFD: " & exOccFD.Message
                        End Try
                    End If
                    ' Attempt 3: parent File.ReferencedFileDescriptors (full path or filename)
                    If Not bReplaceOk Then
                        Try
                            Dim sOldNameOnly As String = System.IO.Path.GetFileName(sOldFullName)
                            For Each oFD As FileDescriptor In oCompDef.Document.File.ReferencedFileDescriptors
                                Try
                                    Dim sFdFull As String = ""
                                    Try : sFdFull = oFD.FullFileName : Catch : Continue For : End Try
                                    Dim bFdMatch As Boolean = (String.Compare(sFdFull, sOldFullName, True) = 0)
                                    If Not bFdMatch AndAlso sOldNameOnly <> "" Then
                                        Try
                                            bFdMatch = (String.Compare(System.IO.Path.GetFileName(sFdFull), sOldNameOnly, True) = 0)
                                        Catch
                                        End Try
                                    End If
                                    If bFdMatch Then
                                        oFD.ReplaceReference(sNewFullName)
                                        Try : oRepOcc.Name = System.IO.Path.GetFileNameWithoutExtension(sNewFullName) : Catch : End Try
                                        bReplaceOk = True
                                        oLog.Append(vbCrLf & "  FILE-DESCRIPTOR REPOINT: " & sOldFileName & sExt & "  -->  " & sNewFileName & sExt & "  [in " & System.IO.Path.GetFileName(sParentFullForReplace) & "]")
                                        Exit For
                                    End If
                                Catch
                                End Try
                            Next
                        Catch exFD As Exception
                            sReplaceFailMsg = sReplaceFailMsg & "; ParentFD: " & exFD.Message
                        End Try
                    End If
                    ' Attempt 4: Replace again after RO clear
                    If Not bReplaceOk Then
                        Try
                            If sParentFullForReplace <> "" Then
                                Dim oPa2 As System.IO.FileAttributes = System.IO.File.GetAttributes(sParentFullForReplace)
                                If (oPa2 And System.IO.FileAttributes.ReadOnly) = System.IO.FileAttributes.ReadOnly Then
                                    System.IO.File.SetAttributes(sParentFullForReplace, oPa2 And Not System.IO.FileAttributes.ReadOnly)
                                End If
                            End If
                        Catch
                        End Try
                        Try
                            oRepOcc.Replace(sNewFullName, False)
                            Try : oRepOcc.Name = System.IO.Path.GetFileNameWithoutExtension(sNewFullName) : Catch : End Try
                            bReplaceOk = True
                        Catch exR2 As Exception
                            sReplaceFailMsg = sReplaceFailMsg & "; retry: " & exR2.Message
                        End Try
                    End If
                    If bReplaceOk Then
                        ' CLEANUP: delete old file if it landed in same folder as new.
                        If String.Compare(System.IO.Path.GetDirectoryName(sOldFullName), _
                                          System.IO.Path.GetDirectoryName(sNewFullName), True) = 0 AndAlso _
                           String.Compare(sOldFullName, sNewFullName, True) <> 0 AndAlso _
                           Not IsInExcludedFolder(sOldFullName) AndAlso _
                           System.IO.File.Exists(sOldFullName) Then
                            Try
                                System.IO.File.Delete(sOldFullName)
                                oLog.Append(vbCrLf & "  CLEANUP: deleted old copy from target folder: " & sOldFileName & sExt)
                            Catch exDel As Exception
                                oLog.Append(vbCrLf & "  CLEANUP WARNING: could not delete old copy: " & sOldFileName & sExt & " (" & exDel.Message & ")")
                            End Try
                        End If
                        oRenameMap(sOldFullName) = sNewFullName
                        iCount = iCount + 1
                        If bLocalizeOnly Then
                            oLog.Append(vbCrLf & "LOCALIZED (name unchanged" & IIf(bRoutedToNonStd, ", routed to Non Std Parts", "") & "): " & sOldFileName & sExt & "  -  local copy already existed, repointed only")
                        Else
                            oLog.Append(vbCrLf & sOldFileName & sExt & "   -->   " & sNewFileName & sExt & IIf(bRoutedToNonStd, "  (routed to Non Std Parts)", "") & "  (already existed - replaced only, not re-copied)")
                        End If
                        bChangedHere = True
                        bDidRename = True
                    Else
                        ' Was silent before — this is why PJ174-16-075 stayed in 22-000
                        oLog.Append(vbCrLf & "FAILED to repoint existing target for: " & sOldFileName & sExt & "  -->  " & sNewFileName & sExt & "  (target exists on disk; all replace methods failed" & IIf(sReplaceFailMsg <> "", ": " & sReplaceFailMsg, "") & ")  [parent: " & System.IO.Path.GetFileName(sParentFullForReplace) & "]")
                        If oNeedsCheckout IsNot Nothing AndAlso sParentFullForReplace <> "" Then
                            oNeedsCheckout.Add(sParentFullForReplace)
                        End If
                        CheckContinueOrExit( _
                            "Could not repoint: " & sOldFileName & sExt & " -> " & sNewFileName & sExt & vbCrLf & _
                            "Parent assembly: " & System.IO.Path.GetFileName(sParentFullForReplace) & vbCrLf & _
                            "Usually means the parent is checked IN (Vault) or read-only." & vbCrLf & _
                            "Check out the parent, then re-run.", sLogFilePath)
                    End If
                Else
                    Try
                        Try
                            System.IO.File.AppendAllText(sLogFilePath, "      " & DateTime.Now.ToString("HH:mm:ss.fff") & "  SaveAs starting: " & sOldFileName & sExt & "  ->  " & sNewFileName & sExt & vbCrLf)
                        Catch
                        End Try

                        ' PART FILES: use File.Copy first, SaveAs only as fallback.
                        ' SaveAs on .ipt files can crash Inventor hard (no exception
                        ' thrown - process terminates) when the file has certain
                        ' geometry, iLogic rules, or adaptive/Frame Generator
                        ' relationships. File.Copy is always safe - an OS byte copy
                        ' that never touches Inventor COM. For parts, derive source
                        ' and param table links are fixed AFTER the copy by
                        ' ProcessDerivedSource/UpdateLinkedParams, so File.Copy first
                        ' is equally correct and eliminates the crash risk entirely.
                        Dim bMode1SaveAsOk As Boolean = False
                        Dim bCopiedViaFileCopy As Boolean = False  ' True when .ipt used File.Copy (not SaveAs)
                        If sExt.ToUpper() = ".IPT" Then
                            ' PART: File.Copy first (safe, no Inventor COM involved)
                            ' Use overwrite=True so a re-run doesn't throw "file exists"
                            ' and fall through to SaveAs, which triggers Inventor's own
                            ' "Confirm Save As / file already exists" dialog.
                            Try
                                If Not System.IO.Directory.Exists(System.IO.Path.GetDirectoryName(sNewFullName)) Then
                                    System.IO.Directory.CreateDirectory(System.IO.Path.GetDirectoryName(sNewFullName))
                                End If
                                System.IO.File.Copy(sOldFullName, sNewFullName, True)
                                bMode1SaveAsOk = System.IO.File.Exists(sNewFullName)
                                If bMode1SaveAsOk Then
                                    bCopiedViaFileCopy = True
                                    Try
                                        System.IO.File.AppendAllText(sLogFilePath, "      " & DateTime.Now.ToString("HH:mm:ss.fff") & "  File.Copy succeeded (.ipt - safe path)." & vbCrLf)
                                    Catch
                                    End Try
                                End If
                            Catch exCopyFirst As Exception
                                ' File.Copy failed - try SaveAs as fallback
                                Try
                                    System.IO.File.AppendAllText(sLogFilePath, "      " & DateTime.Now.ToString("HH:mm:ss.fff") & "  File.Copy failed (" & exCopyFirst.Message & ") - trying SaveAs fallback." & vbCrLf)
                                Catch
                                End Try
                                Try
                                    oRefDoc.SaveAs(sNewFullName, True)
                                    bMode1SaveAsOk = True
                                    Try
                                        System.IO.File.AppendAllText(sLogFilePath, "      " & DateTime.Now.ToString("HH:mm:ss.fff") & "  SaveAs fallback finished." & vbCrLf)
                                    Catch
                                    End Try
                                Catch exSaveAsFb As Exception
                                    Try
                                        System.IO.File.AppendAllText(sLogFilePath, "      " & DateTime.Now.ToString("HH:mm:ss.fff") & "  SaveAs fallback also threw: " & exSaveAsFb.Message & vbCrLf)
                                    Catch
                                    End Try
                                End Try
                            End Try
                        Else
                            ' ASSEMBLY (.iam etc): SaveAs(False) = "Save As" to new path.
                            ' SaveAs(True) = "Save Copy As" - Vault BLOCKS on checked-in files.
                            ' SaveAs(False) renames doc in session to new path - Vault allows this.
                            Try
                                oRefDoc.SaveAs(sNewFullName, False)
                                bMode1SaveAsOk = True
                                Try
                                    System.IO.File.AppendAllText(sLogFilePath, "      " & DateTime.Now.ToString("HH:mm:ss.fff") & "  SaveAs finished." & vbCrLf)
                                Catch
                                End Try
                            Catch exSaveAs As Exception
                                Try
                                    System.IO.File.AppendAllText(sLogFilePath, "      " & DateTime.Now.ToString("HH:mm:ss.fff") & "  SaveAs threw (" & exSaveAs.Message & ") - will attempt File.Copy fallback." & vbCrLf)
                                Catch
                                End Try
                            End Try
                            ' File.Copy fallback for assemblies (overwrite=True: re-run safe)
                            If Not bMode1SaveAsOk OrElse Not System.IO.File.Exists(sNewFullName) Then
                                Try
                                    System.IO.File.Copy(sOldFullName, sNewFullName, True)
                                    Try
                                        System.IO.File.AppendAllText(sLogFilePath, "      " & DateTime.Now.ToString("HH:mm:ss.fff") & "  File.Copy fallback succeeded (SaveAs threw or produced no file)." & vbCrLf)
                                    Catch
                                    End Try
                                    If System.IO.File.Exists(sNewFullName) Then bMode1SaveAsOk = True
                                Catch exCopy As Exception
                                    oLog.Append(vbCrLf & "FAILED: " & sOldFileName & sExt & " (SaveAs threw E_FAIL, File.Copy fallback also failed: " & exCopy.Message & ")")
                                    Try
                                        System.IO.File.AppendAllText(sLogFilePath, "      " & DateTime.Now.ToString("HH:mm:ss.fff") & "  File.Copy fallback FAILED: " & exCopy.Message & vbCrLf)
                                    Catch
                                    End Try
                                    GoTo NextOccurrence
                                End Try
                            End If
                        End If

                        ' COLLISION CHECK: if target already exists AND was created
                        ' by a DIFFERENT source this run, apply Option 2 disambiguation:
                        ' insert the numeric digits from the old prefix into the new name.
                        ' e.g. PJ00174-XXX-01 + PJ00145-XXX-01 → 
                        '      PJ00999-174-XXX-01 + PJ00999-145-XXX-01
                        If System.IO.File.Exists(sNewFullName) Then
                            ' Check if this target was mapped from a DIFFERENT source
                            Dim bCollision As Boolean = False
                            For Each kvp As System.Collections.Generic.KeyValuePair(Of String, String) In oRenameMap
                                If String.Compare(kvp.Value, sNewFullName, True) = 0 AndAlso _
                                   String.Compare(kvp.Key, sOldFullName, True) <> 0 Then
                                    bCollision = True
                                    Exit For
                                End If
                            Next
                            If bCollision Then
                                ' Extract numeric suffix from old prefix (e.g. "174" from "PJ00174")
                                Dim sOldPrefix As String = sFind  ' the current batch find token
                                Dim sNumericSuffix As String = ""
                                Try
                                    Dim sDigits As String = ""
                                    For Each ch As Char In sOldPrefix
                                        If Char.IsDigit(ch) Then sDigits = sDigits & ch
                                    Next
                                    ' Strip leading zeros but keep at least one digit
                                    sNumericSuffix = sDigits.TrimStart("0"c)
                                    If sNumericSuffix = "" Then sNumericSuffix = sDigits
                                Catch
                                End Try
                                If sNumericSuffix <> "" Then
                                    ' Insert numeric suffix after new prefix separator
                                    ' PJ00999-XXX → PJ00999-174-XXX
                                    Dim sNewFileNoExt As String = System.IO.Path.GetFileNameWithoutExtension(sNewFullName)
                                    Dim iSepIdx As Integer = sNewFileNoExt.IndexOf("-")
                                    If iSepIdx >= 0 Then
                                        sNewFileNoExt = sNewFileNoExt.Substring(0, iSepIdx + 1) & sNumericSuffix & "-" & sNewFileNoExt.Substring(iSepIdx + 1)
                                    Else
                                        sNewFileNoExt = sNewFileNoExt & "-" & sNumericSuffix
                                    End If
                                    Dim sDisambigFull As String = System.IO.Path.Combine(System.IO.Path.GetDirectoryName(sNewFullName), sNewFileNoExt & sExt)
                                    oLog.Append(vbCrLf & "COLLISION: '" & sOldFileName & sExt & "' and an earlier source both map to '" & System.IO.Path.GetFileName(sNewFullName) & "' - disambiguating to '" & sNewFileNoExt & sExt & "'")
                                    sNewFullName = sDisambigFull
                                    sNewFileName = sNewFileNoExt
                                Else
                                    oLog.Append(vbCrLf & "COLLISION (no numeric suffix found to disambiguate): '" & sOldFileName & sExt & "' skipped - target already exists from another source.")
                                    GoTo NextOccurrence
                                End If
                            End If
                        End If

                        If Not System.IO.File.Exists(sNewFullName) Then
                            oLog.Append(vbCrLf & "FAILED: " & sOldFileName & sExt & " (file not on disk after SaveAs + File.Copy)")
                            CheckContinueOrExit("Could not copy: " & sOldFileName & sExt, sLogFilePath)
                            GoTo NextOccurrence
                        End If

                        ' Replace and node rename in their own Try/Catch so a
                        ' Replace() failure (e.g. parent assembly checked in to
                        ' Vault) doesn't trigger the outer Catch and skip the
                        ' log/cleanup steps below.
                        '
                        ' DA PROTECTION NOTE: For DA-managed occurrences (e.g. Frame Generator
                        ' structural members sitting as direct occurrences in a parent assembly),
                        ' oRepOcc.Replace() can return silently without throwing AND without
                        ' actually repointing - bReplaceOk goes True but the occurrence still
                        ' points at the old path. We detect this with a post-Replace verification
                        ' check and fall through to FD-based repoint attempts if needed.
                        Dim bReplaceOk As Boolean = False
                        Dim sReplaceFailMsg As String = ""
                        Try
                            oRepOcc.Replace(sNewFullName, False)
                            ' Post-Replace verification: confirm the occurrence actually moved.
                            ' DA protection can cause Replace() to return silently without repointing.
                            Dim sVerifyPath As String = ""
                            Try
                                sVerifyPath = oRepOcc.ReferencedFileDescriptor.FullFileName
                            Catch
                            End Try
                            If String.Compare(sVerifyPath, sNewFullName, True) = 0 Then
                                bReplaceOk = True
                            Else
                                ' Replace() returned but occurrence still points at old path - DA blocked it silently.
                                sReplaceFailMsg = "Replace: silently blocked by DA (occurrence still at old path after Replace)"
                                oLog.Append(vbCrLf & "  DA-SILENT-BLOCK detected: oRepOcc.Replace() returned but occurrence still points at old path - trying FD fallbacks: " & sOldFileName & sExt)
                            End If
                        Catch exReplace As Exception
                            sReplaceFailMsg = "Replace: " & exReplace.Message
                        End Try
                        ' Attempt 2: occurrence's own ReferencedFileDescriptor
                        If Not bReplaceOk Then
                            Try
                                Dim oOccFD As FileDescriptor = Nothing
                                Try : oOccFD = oRepOcc.ReferencedFileDescriptor : Catch : oOccFD = Nothing : End Try
                                If oOccFD IsNot Nothing Then
                                    oOccFD.ReplaceReference(sNewFullName)
                                    bReplaceOk = True
                                    oLog.Append(vbCrLf & "  OCC-FD REPOINT (DA fallback): " & sOldFileName & sExt & "  -->  " & sNewFileName & sExt & "  [in " & System.IO.Path.GetFileName(oCompDef.Document.FullFileName) & "]")
                                End If
                            Catch exOccFD As Exception
                                sReplaceFailMsg = sReplaceFailMsg & "; OccFD: " & exOccFD.Message
                            End Try
                        End If
                        ' Attempt 3: parent File.ReferencedFileDescriptors loop (full path or filename match)
                        If Not bReplaceOk Then
                            Try
                                Dim sOldNameOnly As String = System.IO.Path.GetFileName(sOldFullName)
                                For Each oFD As FileDescriptor In oCompDef.Document.File.ReferencedFileDescriptors
                                    Try
                                        Dim sFdFull As String = ""
                                        Try : sFdFull = oFD.FullFileName : Catch : Continue For : End Try
                                        Dim bFdMatch As Boolean = (String.Compare(sFdFull, sOldFullName, True) = 0)
                                        If Not bFdMatch AndAlso sOldNameOnly <> "" Then
                                            Try
                                                bFdMatch = (String.Compare(System.IO.Path.GetFileName(sFdFull), sOldNameOnly, True) = 0)
                                            Catch
                                            End Try
                                        End If
                                        If bFdMatch Then
                                            oFD.ReplaceReference(sNewFullName)
                                            bReplaceOk = True
                                            oLog.Append(vbCrLf & "  FILE-DESCRIPTOR REPOINT (DA fallback): " & sOldFileName & sExt & "  -->  " & sNewFileName & sExt & "  [in " & System.IO.Path.GetFileName(oCompDef.Document.FullFileName) & "]")
                                            Exit For
                                        End If
                                    Catch
                                    End Try
                                Next
                            Catch exFD As Exception
                                sReplaceFailMsg = sReplaceFailMsg & "; ParentFD: " & exFD.Message
                            End Try
                        End If
                        If Not bReplaceOk Then
                            oLog.Append(vbCrLf & "FAILED to repoint occurrence after copy: " & sOldFileName & sExt & " (" & sReplaceFailMsg & ") - parent assembly: " & System.IO.Path.GetFileName(oCompDef.Document.FullFileName) & " - re-run after checking out parent assembly")
                        End If
                        ' Rename the browser node to match the new filename so the
                        ' browser stays in sync with what's actually on disk.
                        If bReplaceOk Then
                            Try
                                oRepOcc.Name = System.IO.Path.GetFileNameWithoutExtension(sNewFullName)
                            Catch
                            End Try
                        End If
                        oRenameMap(sOldFullName) = sNewFullName
                        iCount = iCount + 1

                        ' FIX 4: Process derive sources on the new copy immediately.
                        ' File.Copy'd parts are NOT opened in the Inventor session,
                        ' so AllReferencedDocuments (post-traversal pass) cannot see
                        ' them. Open the new copy now and fix its derive sources
                        ' (xlsx param tables, ipt derived parts) right away.
                        If sExt.ToUpper() = ".IPT" AndAlso bCopiedViaFileCopy Then
                            Try
                                Dim bDeriveOpenedHere As Boolean = False
                                Dim oNewPartDoc As Document = OpenDocTracked(sNewFullName, bDeriveOpenedHere)
                                If oNewPartDoc IsNot Nothing Then
                                    ' Clear read-only on the new copy before modifying
                                    Try
                                        Dim oNewAttrs As System.IO.FileAttributes = System.IO.File.GetAttributes(sNewFullName)
                                        If (oNewAttrs And System.IO.FileAttributes.ReadOnly) = System.IO.FileAttributes.ReadOnly Then
                                            System.IO.File.SetAttributes(sNewFullName, oNewAttrs And Not System.IO.FileAttributes.ReadOnly)
                                        End If
                                    Catch
                                    End Try
                                    Dim bDeriveFixed As Boolean = False
                                    Try
                                        bDeriveFixed = ProcessDerivedSource(oNewPartDoc, sFind, sReplace, bUseContainsMode, sTargetFolder, sTopAssemblyFullName, oLog, iCount, oRenameMap, sLogFilePath)
                                    Catch exDs As Exception
                                        oLog.Append(vbCrLf & "  DERIVE FIX on new copy FAILED: " & sNewFileName & sExt & " (" & exDs.Message & ")")
                                    End Try
                                    If bDeriveFixed Then
                                        Try
                                            oNewPartDoc.Save2(False)
                                        Catch exSv As Exception
                                            oLog.Append(vbCrLf & "  DERIVE FIX save FAILED: " & sNewFileName & sExt & " (" & exSv.Message & ")")
                                        End Try
                                    End If
                                    CloseIfOpenedHere(oNewPartDoc, bDeriveOpenedHere)
                                    oNewPartDoc = Nothing
                                End If
                            Catch exOpen As Exception
                                oLog.Append(vbCrLf & "  DERIVE FIX: could not open new copy for derive processing: " & sNewFileName & sExt & " (" & exOpen.Message & ")")
                            End Try
                        End If

                        ' CLEANUP: if the old file ended up in the SAME folder as the
                        ' new file (e.g. both in the target folder after a SaveAs that
                        ' landed there), delete the old copy. Having both PJ00174-xxx
                        ' and PJ00777-xxx in the same folder causes E_FAIL on subsequent
                        ' Replace() calls because Inventor/Vault sees the ambiguity.
                        ' Only delete when: same folder, different name, Replace succeeded,
                        ' and the old file is NOT in an excluded/Vault-managed location.
                        If String.Compare(System.IO.Path.GetDirectoryName(sOldFullName), _
                                          System.IO.Path.GetDirectoryName(sNewFullName), True) = 0 AndAlso _
                           String.Compare(sOldFullName, sNewFullName, True) <> 0 AndAlso _
                           Not IsInExcludedFolder(sOldFullName) AndAlso _
                           System.IO.File.Exists(sOldFullName) Then
                            Try
                                System.IO.File.Delete(sOldFullName)
                                oLog.Append(vbCrLf & "  CLEANUP: deleted old copy from target folder: " & sOldFileName & sExt)
                            Catch exDel As Exception
                                oLog.Append(vbCrLf & "  CLEANUP WARNING: could not delete old copy: " & sOldFileName & sExt & " (" & exDel.Message & ")")
                            End Try
                        End If

                        If bLocalizeOnly Then
                            oLog.Append(vbCrLf & "LOCALIZED (name unchanged" & IIf(bRoutedToNonStd, ", routed to Non Std Parts", "") & "): " & sOldFileName & sExt & "  -  copied from " & System.IO.Path.GetDirectoryName(sOldFullName) & IIf(Not bReplaceOk, "  [occurrence repoint failed - re-run after checking out parent assembly]", ""))
                        Else
                            oLog.Append(vbCrLf & sOldFileName & sExt & "   -->   " & sNewFileName & sExt & IIf(bRoutedToNonStd, "  (routed to Non Std Parts)", "") & IIf(Not bMode1SaveAsOk, "  [copied via File.Copy - re-run Mode 3 to fix internal references]", "") & IIf(Not bReplaceOk, "  [occurrence repoint failed - re-run after checking out parent assembly]", ""))
                        End If
                        If bReplaceOk Then
                            bChangedHere = True
                            bDidRename = True
                        End If
                    Catch ex As Exception
                        oLog.Append(vbCrLf & "FAILED: " & sOldFileName & sExt & " (" & ex.Message & ")")
                        Try
                            System.IO.File.AppendAllText(sLogFilePath, "      " & DateTime.Now.ToString("HH:mm:ss.fff") & "  SaveAs FAILED: " & ex.Message & vbCrLf)
                        Catch
                        End Try
                    End Try
                End If
            End If

            If Not bDidRename AndAlso bChildChanged Then
                ' Name unchanged (either didn't match, or was safety-skipped),
                ' but something below it changed - save in place so its
                ' internal references stay correct.
                If Not oSavedInPlace.Contains(sOldFullName) Then

                    ' --- Pre-check read-only BEFORE attempting Save(). A
                    ' checked-in Vault file is read-only on disk, and a
                    ' Save() failure on one of these can surface as
                    ' Inventor's own native error dialog rather than a
                    ' clean, catchable exception - Try/Catch alone can't
                    ' suppress that. Checking first and simply not
                    ' attempting the save avoids ever triggering it.
                    Dim bSubIsReadOnly As Boolean = False
                    Try
                        Dim oSubAttrs As System.IO.FileAttributes = System.IO.File.GetAttributes(sOldFullName)
                        bSubIsReadOnly = ((oSubAttrs And System.IO.FileAttributes.ReadOnly) = System.IO.FileAttributes.ReadOnly)
                    Catch
                        ' If the check itself fails, fall through and let
                        ' the Save() attempt below report whatever happens.
                    End Try

                    If bSubIsReadOnly Then
                        oLog.Append(vbCrLf & "SKIPPED SAVE (checked-in/read-only in Vault): " & sOldFileName & sExt & " - its internal reference to a renamed child is updated IN MEMORY and will still be correct if you check this file out and save it manually, but it wasn't saved by this run.")
                        Try
                            System.IO.File.AppendAllText(sLogFilePath, "      " & DateTime.Now.ToString("HH:mm:ss.fff") & "  SKIPPED SAVE (read-only): " & sOldFullName & vbCrLf)
                        Catch
                        End Try
                    Else
                        ' Clear read-only attribute before Save() - Vault add-in
                        ' can intercept Save() on local files that aren't checked
                        ' out, causing E_FAIL even when the file isn't read-only.
                        Try
                            Dim oSubAttrsWrite As System.IO.FileAttributes = System.IO.File.GetAttributes(sOldFullName)
                            If (oSubAttrsWrite And System.IO.FileAttributes.ReadOnly) = System.IO.FileAttributes.ReadOnly Then
                                System.IO.File.SetAttributes(sOldFullName, oSubAttrsWrite And Not System.IO.FileAttributes.ReadOnly)
                            End If
                        Catch
                        End Try
                        Try
                            oRefDoc.Save()
                            oSavedInPlace.Add(sOldFullName)
                            oLog.Append(vbCrLf & "Updated internal references (name unchanged): " & sOldFileName & sExt)
                        Catch ex As Exception
                            oLog.Append(vbCrLf & "FAILED to save updated sub-assembly: " & sOldFileName & sExt & " (" & ex.Message & ")")
                        End Try
                    End If
                End If
            End If

            ' --- DECISION LOG FLUSH: write the CURRENT full decision log
            ' (oLog - matches/renames/exclusions/safety-skips, everything
            ' shown in the final summary popup) to disk after each
            ' occurrence is processed. Previously this only ever existed
            ' in memory until the final popup, so if the run needed
            ' diagnosing from the disk log alone, none of the actual
            ' match/rename/exclude reasoning was visible - only timing.
            Try
                System.IO.File.WriteAllText(System.IO.Path.Combine(System.IO.Path.GetDirectoryName(sLogFilePath), System.IO.Path.GetFileNameWithoutExtension(sLogFilePath) & "_Decisions.txt"), oLog.ToString())
            Catch
            End Try

NextOccurrence:
        PeriodicGcTick()
        If IsExitRequested() Then Exit For
        Next

        ' --- SECOND PASS: fix every remaining raw occurrence at this level ---
        ' The loop above only processes ONE representative occurrence per
        ' unique underlying file. That's wrong for the Replace() step
        ' whenever the SAME file is used by more than one occurrence at this
        ' level - e.g. a Component Pattern feature, which creates many
        ' separate occurrences all pointing at the same seed file. This pass
        ' walks every raw occurrence and repoints any whose current file
        ' matches something already renamed this run.
        For Each oOcc In oCompDef.Occurrences

            If oOcc.Suppressed Then Continue For

            Dim oOccRefDoc As Document = Nothing
            Try
                oOccRefDoc = oOcc.Definition.Document
            Catch
                Continue For
            End Try

            Dim sOccCurrentFullName As String = oOccRefDoc.FullFileName
            If sOccCurrentFullName = "" Then Continue For

            ' Same synthetic-name guard as the main loop above - a pattern-
            ' member occurrence's reported name here will never legitimately
            ' match a real key in oRenameMap anyway (that map is only ever
            ' populated from real, vetted file paths now), but skip it
            ' explicitly rather than relying on that lookup simply missing.
            If IsSyntheticPatternMemberName(sOccCurrentFullName) Then Continue For

            If oRenameMap.ContainsKey(sOccCurrentFullName) Then
                Dim sOccNewName As String = oRenameMap(sOccCurrentFullName)
                Try
                    oOcc.Replace(sOccNewName, False)
                    iCount = iCount + 1
                    oLog.Append(vbCrLf & "Repointed additional instance (e.g. pattern member) '" & oOcc.Name & "'  -->  " & System.IO.Path.GetFileName(sOccNewName))
                    bChangedHere = True
                Catch ex As Exception
                    oLog.Append(vbCrLf & "FAILED to repoint additional instance '" & oOcc.Name & "' (" & ex.Message & ")")
                End Try
            End If

        Next

    Finally
        ' RE-SUPPRESS: restore any occurrences suppressed before this call.
        If oSuppressedInLevel.Count > 0 Then
            Try
                System.IO.File.AppendAllText(sLogFilePath, DateTime.Now.ToString("HH:mm:ss.fff") & "  Re-suppressing " & oSuppressedInLevel.Count & " occurrence(s)." & vbCrLf)
            Catch
            End Try
            For Each oSuppOcc As ComponentOccurrence In oSuppressedInLevel
                Try
                    oSuppOcc.Suppress()
                Catch exResupp As Exception
                    Try
                        System.IO.File.AppendAllText(sLogFilePath, DateTime.Now.ToString("HH:mm:ss.fff") & "  WARNING: could not re-suppress " & oSuppOcc.Name & ": " & exResupp.Message & vbCrLf)
                    Catch
                    End Try
                End Try
            Next
        End If
        If Not bSkipCycleGuardEntry Then
            oProcessedResults(sThisLevelFullName) = bChangedHere
            oVisitedLevels.Remove(sThisLevelFullName)
            oPathStack.RemoveAt(oPathStack.Count - 1)
        End If
        Try
            System.IO.File.AppendAllText(sLogFilePath, DateTime.Now.ToString("HH:mm:ss.fff") & "  DONE: " & System.IO.Path.GetFileName(sThisLevelFullName) & "  (changed=" & bChangedHere.ToString() & ")" & vbCrLf)
        Catch
        End Try
    End Try

    Return bChangedHere

End Function


' Checks a part's DERIVED source reference(s). If a referenced source
' file's name STARTS WITH sFind: repoints to an existing new-name copy
' if one is already on disk, or copies the OLD source to the new name
' and repoints to that new copy. Feeds into the same oRenameMap as
' regular occurrences, so a source used by multiple parts is only ever
' copied once. Returns True if anything was changed.
Function ProcessDerivedSource(oPartDoc As Document, sFind As String, sReplace As String, bUseContainsMode As Boolean, sTargetFolder As String, sTopAssemblyFullName As String, oLog As System.Text.StringBuilder, ByRef iCount As Integer, ByRef oRenameMap As System.Collections.Generic.Dictionary(Of String, String), sLogFilePath As String) As Boolean

    Dim bChanged As Boolean = False

    ' PRE-PASS: detect and temporarily unsuppress any suppressed derive feature
    ' OR suppressed link (SuppressLinkToFile). When the link/feature is suppressed,
    ' the source file descriptor may return empty path - unsuppressing first forces
    ' Inventor to load the reference so the rename/repoint below can see it.
    Dim oPreUnsuppressedFeature As Object = Nothing
    Dim oPreUnsuppressedLinkComps As New System.Collections.Generic.List(Of Object)  ' DerivedPart/Asm with SuppressLinkToFile restored later
    If oPartDoc.DocumentType = kPartDocumentObject Then
        Try
            Dim oPrePartDef As PartComponentDefinition = oPartDoc.ComponentDefinition
            If oPrePartDef.BaseComponent IsNot Nothing Then
                Dim bIsInactive As Boolean = False
                Try : bIsInactive = Not oPrePartDef.BaseComponent.IsActive : Catch : End Try
                If bIsInactive Then
                    Try
                        For Each oFeat As Object In oPrePartDef.Features
                            Try
                                Dim bFS As Boolean = False
                                Try : bFS = oFeat.Suppressed : Catch : End Try
                                If bFS Then
                                    oFeat.Suppressed = False
                                    oPreUnsuppressedFeature = oFeat
                                    oLog.Append(vbCrLf & "  DERIVE PRE-UNSUPPRESS: temporarily unsuppressed derive feature in " & System.IO.Path.GetFileName(oPartDoc.FullFileName))
                                    Exit For
                                End If
                            Catch
                            End Try
                        Next
                    Catch
                    End Try
                    If oPreUnsuppressedFeature Is Nothing Then
                        Try : oPrePartDef.BaseComponent.SetActive(True) : Catch : End Try
                    End If
                End If
            End If

            ' Also unsuppress "Suppress Link With Base Component" on every derived part/asm
            Try
                For Each oDP As DerivedPartComponent In oPrePartDef.ReferenceComponents.DerivedPartComponents
                    Dim bLinkSup As Boolean = False
                    Try : bLinkSup = oDP.SuppressLinkToFile : Catch : End Try
                    If bLinkSup Then
                        Try
                            oDP.SuppressLinkToFile = False
                            oPreUnsuppressedLinkComps.Add(oDP)
                            oLog.Append(vbCrLf & "  DERIVE PRE-UNSUPPRESS LINK: temporarily unsuppressed link on '" & oDP.Name & "' in " & System.IO.Path.GetFileName(oPartDoc.FullFileName))
                        Catch
                        End Try
                    End If
                Next
            Catch
            End Try
            Try
                For Each oDA As DerivedAssemblyComponent In oPrePartDef.ReferenceComponents.DerivedAssemblyComponents
                    Dim bLinkSup As Boolean = False
                    Try : bLinkSup = oDA.SuppressLinkToFile : Catch : End Try
                    If bLinkSup Then
                        Try
                            oDA.SuppressLinkToFile = False
                            oPreUnsuppressedLinkComps.Add(oDA)
                            oLog.Append(vbCrLf & "  DERIVE PRE-UNSUPPRESS LINK: temporarily unsuppressed link on '" & oDA.Name & "' in " & System.IO.Path.GetFileName(oPartDoc.FullFileName))
                        Catch
                        End Try
                    End If
                Next
            Catch
            End Try
        Catch
        End Try
    End If

    For Each oFileDesc As FileDescriptor In oPartDoc.File.ReferencedFileDescriptors

        Dim sRefFullName As String = ""
        Try
            sRefFullName = oFileDesc.FullFileName
        Catch
            Continue For
        End Try

        If sRefFullName = "" Then Continue For

        ' --- BROKEN LINK DETECTION: file descriptor returns a path but the
        ' file no longer exists on disk AND it wasn't renamed this run.
        ' This is a static geometry with a dead reference (e.g. a part that
        ' derived from a Vault library source that was never copied locally).
        ' Attempting to repoint a broken link throws COM errors and could
        ' corrupt the part. Skip silently.
        If Not System.IO.File.Exists(sRefFullName) AndAlso Not oRenameMap.ContainsKey(sRefFullName) Then
            ' Double-check it isn't a virtual path (contains wildcards or is very short)
            If Not sRefFullName.Contains("*") AndAlso sRefFullName.Length > 5 Then
                oLog.Append(vbCrLf & "  DERIVED SOURCE (broken link - file missing, skipped): " & System.IO.Path.GetFileName(sRefFullName) & "  [in " & System.IO.Path.GetFileName(oPartDoc.FullFileName) & "]")
            End If
            Continue For
        End If

        ' --- SUPPRESSED DERIVE DETECTION AND HANDLING ---
        ' If the derive feature is suppressed, we must:
        '   1. Detect suppression via BaseComponent.IsActive = False
        '   2. Unsuppress it (so ReplaceReference can work)
        '   3. Repoint the reference (handled below in the normal flow)
        '   4. Re-suppress it afterwards
        ' If the link is BROKEN (source file missing) we skip it - handled
        ' earlier in this loop by the broken link detection block.
        Dim bDeriveSuppressed As Boolean = False
        Dim oSuppressedFeature As Object = Nothing  ' the feature to re-suppress after
        Try
            If oPartDoc.DocumentType = kPartDocumentObject Then
                Dim oPartDefCheck As PartComponentDefinition = oPartDoc.ComponentDefinition
                If oPartDefCheck.BaseComponent IsNot Nothing Then
                    Try
                        bDeriveSuppressed = Not oPartDefCheck.BaseComponent.IsActive
                    Catch
                    End Try
                    If bDeriveSuppressed Then
                        ' Unsuppress: iterate ALL features and unsuppress the first
                        ' suppressed one. We don't filter by type name because
                        ' Inventor's type strings vary by version. The derive feature
                        ' is typically the ONLY suppressed feature in a derive part.
                        Try
                            For Each oFeat As Object In oPartDefCheck.Features
                                Try
                                    Dim bFeatSuppressed As Boolean = False
                                    Try : bFeatSuppressed = oFeat.Suppressed : Catch : End Try
                                    If bFeatSuppressed Then
                                        oFeat.Suppressed = False
                                        oSuppressedFeature = oFeat
                                        Exit For
                                    End If
                                Catch
                                End Try
                            Next
                        Catch
                        End Try
                        ' Fallback: try SetActive directly on BaseComponent
                        If oSuppressedFeature Is Nothing Then
                            Try : oPartDefCheck.BaseComponent.SetActive(True) : Catch : End Try
                        End If
                    End If
                End If
            End If
        Catch
        End Try

        ' --- EXCLUDED FOLDER: a derived source in a Vault Library, Content
        ' Center, or Jameson Cell Standard folder is never COPIED out. However,
        ' if the source matches the Find pattern AND a renamed copy already exists
        ' in the target folder (created by an earlier run or another rule), we
        ' still repoint to that existing copy. We only truly skip if no renamed
        ' copy exists yet - copying from excluded folders is never safe.
        If IsInExcludedFolder(sRefFullName) Then
            ' Check if a renamed copy already exists in the target folder
            Dim sExRefName As String = System.IO.Path.GetFileNameWithoutExtension(sRefFullName)
            Dim sExExt As String = System.IO.Path.GetExtension(sRefFullName)
            Dim bExMatch As Boolean
            If bUseContainsMode Then
                bExMatch = sExRefName.ToUpper().Contains(sFind.ToUpper())
            Else
                bExMatch = sExRefName.ToUpper().StartsWith(sFind.ToUpper())
            End If
            If bExMatch Then
                Dim sExNewName As String
                If bUseContainsMode Then
                    sExNewName = ReplaceAllCaseInsensitive(sExRefName, sFind, sReplace)
                Else
                    sExNewName = sReplace & sExRefName.Substring(sFind.Length)
                End If
                Dim sExNewFull As String = System.IO.Path.Combine(sTargetFolder, sExNewName & sExExt)
                If System.IO.File.Exists(sExNewFull) AndAlso String.Compare(sExNewFull, sRefFullName, True) <> 0 Then
                    ' Renamed copy exists - repoint to it without copying from the library
                    Try
                        Dim oPartAttrsEx As System.IO.FileAttributes = System.IO.File.GetAttributes(oPartDoc.FullFileName)
                        If (oPartAttrsEx And System.IO.FileAttributes.ReadOnly) = System.IO.FileAttributes.ReadOnly Then
                            System.IO.File.SetAttributes(oPartDoc.FullFileName, oPartAttrsEx And Not System.IO.FileAttributes.ReadOnly)
                        End If
                    Catch
                    End Try
                    Try
                        oFileDesc.ReplaceReference(sExNewFull)
                        oRenameMap(sRefFullName) = sExNewFull
                        iCount = iCount + 1
                        oLog.Append(vbCrLf & "DERIVED SOURCE (library/excluded - repointed to existing renamed copy): " & sExRefName & sExExt & "  -->  " & sExNewName & sExExt & "  [used by " & System.IO.Path.GetFileName(oPartDoc.FullFileName) & "]")
                        bChanged = True
                    Catch ex As Exception
                        oLog.Append(vbCrLf & "FAILED to repoint excluded-folder derived source to renamed copy: " & sExRefName & sExExt & " (" & ex.Message & ")")
                    End Try
                End If
            End If
            Continue For  ' never copy FROM an excluded folder, regardless
        End If

        ' --- Already in this assembly's official Non Std Parts folder - MODE 1 ONLY, same reasoning as ProcessLevel above ---
        If Not bUseContainsMode AndAlso String.Compare(System.IO.Path.GetDirectoryName(sRefFullName), System.IO.Path.Combine(sTargetFolder, "Non Std Parts"), True) = 0 Then Continue For

        ' --- Already handled elsewhere in the tree this run? ---
        If oRenameMap.ContainsKey(sRefFullName) Then
            Dim sKnownNewName As String = oRenameMap(sRefFullName)
            ' Clear read-only on the part before ReplaceReference - same
            ' fix as the main copy path. Parts File.Copy'd from Vault or
            ' with Lifecycle locks may be read-only.
            Try
                Dim oPartAttrsRM As System.IO.FileAttributes = System.IO.File.GetAttributes(oPartDoc.FullFileName)
                If (oPartAttrsRM And System.IO.FileAttributes.ReadOnly) = System.IO.FileAttributes.ReadOnly Then
                    System.IO.File.SetAttributes(oPartDoc.FullFileName, oPartAttrsRM And Not System.IO.FileAttributes.ReadOnly)
                End If
            Catch
            End Try
            Try
                oFileDesc.ReplaceReference(sKnownNewName)
                oLog.Append(vbCrLf & "Re-pointed derived source in " & System.IO.Path.GetFileName(oPartDoc.FullFileName) & " to already-renamed file: " & System.IO.Path.GetFileName(sKnownNewName))
                bChanged = True
            Catch ex As Exception
                oLog.Append(vbCrLf & "FAILED to re-point derived source to " & System.IO.Path.GetFileName(sKnownNewName) & " (" & ex.Message & ")")
            End Try
            Continue For
        End If

        Dim sRefFileName As String = System.IO.Path.GetFileNameWithoutExtension(sRefFullName)
        Dim sExt As String = System.IO.Path.GetExtension(sRefFullName)

        ' Mode 1: STARTS WITH, rebuild from the remainder. Mode 2: CONTAINS,
        ' swap just the matched segment wherever it appears.
        Dim bIsMatch As Boolean
        If bUseContainsMode Then
            bIsMatch = sRefFileName.ToUpper().Contains(sFind.ToUpper())
        Else
            bIsMatch = sRefFileName.ToUpper().StartsWith(sFind.ToUpper())
        End If
        If Not bIsMatch Then Continue For

        Dim sNewFileName As String
        If bUseContainsMode Then
            sNewFileName = Trim(ReplaceAllCaseInsensitive(sRefFileName, sFind, sReplace)).Replace("_ ", "_").Replace("  ", " ")
        Else
            sNewFileName = Trim(sReplace & sRefFileName.Substring(sFind.Length)).Replace("_ ", "_").Replace("  ", " ")
        End If

        ' Route to THIS assembly's own "Non Std Parts" folder if the
        ' source currently lives in a folder named that - same reasoning
        ' as the main rename logic in ProcessLevel.
        Dim sEffectiveTargetFolder As String = GetEffectiveTargetFolder(sRefFullName, sTargetFolder)
        Dim bRoutedToNonStd As Boolean = (String.Compare(sEffectiveTargetFolder, sTargetFolder, True) <> 0)
        Dim sNewFullName As String = System.IO.Path.Combine(sEffectiveTargetFolder, sNewFileName & sExt)

        ' --- SAFETY: same top-assembly self-reference check as the main
        ' rename logic above - a derived source could theoretically
        ' collide with the top assembly's own name too.
        If String.Compare(sNewFullName, sTopAssemblyFullName, True) = 0 Then
            oLog.Append(vbCrLf & "SAFETY SKIP: computed new name for derived source '" & sRefFileName & sExt & "' matches the TOP ASSEMBLY'S OWN FILE (" & System.IO.Path.GetFileName(sTopAssemblyFullName) & ") - refusing to repoint. Left unchanged - check this one manually. [used by " & System.IO.Path.GetFileName(oPartDoc.FullFileName) & "]")
            Continue For
        End If

        If System.IO.File.Exists(sNewFullName) Then
            ' Target already exists on disk - don't re-copy, just repoint to it.
            ' Check extension first - non-processable types (dwg, stp etc.)
            ' are skipped entirely even when a renamed copy exists.
            Dim sExtUpperCheck As String = sExt.ToUpper()
            Dim bSkipType As Boolean = Not (sExtUpperCheck = ".IPT" OrElse sExtUpperCheck = ".IAM" OrElse
                                            sExtUpperCheck = ".IPN" OrElse sExtUpperCheck = ".XLSX" OrElse
                                            sExtUpperCheck = ".XLS" OrElse sExtUpperCheck = ".CSV" OrElse
                                            sExtUpperCheck = ".TXT" OrElse sExtUpperCheck = ".JSON" OrElse
                                            sExtUpperCheck = ".XML")
            If bSkipType Then
                oLog.Append(vbCrLf & "DERIVED SOURCE SKIPPED (non-processable type " & sExtUpperCheck & "): " & sRefFileName & sExt & "  [used by " & System.IO.Path.GetFileName(oPartDoc.FullFileName) & "]")
                Continue For
            End If

            ' Clear read-only attribute on the PART FILE first - if it was
            ' File.Copy'd from Vault it may be read-only, causing
            ' ReplaceReference to fail silently.
            Try
                Dim oPartAttrs As System.IO.FileAttributes = System.IO.File.GetAttributes(oPartDoc.FullFileName)
                If (oPartAttrs And System.IO.FileAttributes.ReadOnly) = System.IO.FileAttributes.ReadOnly Then
                    System.IO.File.SetAttributes(oPartDoc.FullFileName, oPartAttrs And Not System.IO.FileAttributes.ReadOnly)
                End If
            Catch
            End Try
            Try
                oFileDesc.ReplaceReference(sNewFullName)
                oRenameMap(sRefFullName) = sNewFullName
                iCount = iCount + 1
                ' Cross-project warning: if the old prefix differs from the new prefix
                ' (e.g. PJ00180 -> PJ00222) AND the target file already existed, it may
                ' be a geometrically different part independently created in the new project.
                ' Flag it so the user can verify manually.
                Dim sCrossProjWarn As String = ""
                If Not bUseContainsMode Then
                    ' StartsWith mode: old prefix = sFind, new prefix = sReplace
                    If String.Compare(sFind, sReplace, True) <> 0 Then
                        sCrossProjWarn = "  *** VERIFY: cross-project repoint to pre-existing file - check geometry matches ***"
                        Try : System.IO.File.AppendAllText(sLogFilePath, "  CROSS-PROJECT REPOINT WARNING: " & sRefFileName & sExt & " -> " & sNewFileName & sExt & " (file already existed - verify geometry is correct)  [used by " & System.IO.Path.GetFileName(oPartDoc.FullFileName) & "]" & vbCrLf) : Catch : End Try
                    End If
                End If
                oLog.Append(vbCrLf & "DERIVED SOURCE" & IIf(bDeriveSuppressed, " (suppressed derive - repointed)", "") & ": " & sRefFileName & sExt & "   -->   " & sNewFileName & sExt & IIf(bRoutedToNonStd, "  (routed to Non Std Parts)", "") & "  (already existed - repointed only)  [used by " & System.IO.Path.GetFileName(oPartDoc.FullFileName) & "]" & sCrossProjWarn)
                bChanged = True
                ' RECURSIVE: chase grandparent derive chain - but ONLY if the new copy
                ' is already open in session (never open cold Centerra files here,
                ' as that causes multi-minute hangs and crashes on deep chains).
                If sExt.ToUpper() = ".IPT" OrElse sExt.ToUpper() = ".IAM" Then
                    Try
                        Dim oNewCopyDocR As Document = Nothing
                        Try : oNewCopyDocR = ThisApplication.Documents.ItemByName(sNewFullName) : Catch : oNewCopyDocR = Nothing : End Try
                        ' Only recurse if already open - never Documents.Open a cold file here
                        If oNewCopyDocR IsNot Nothing Then
                            If ProcessDerivedSource(oNewCopyDocR, sFind, sReplace, bUseContainsMode, sTargetFolder, sTopAssemblyFullName, oLog, iCount, oRenameMap, sLogFilePath) Then
                                bChanged = True
                                Try : oNewCopyDocR.Save2(False) : Catch : End Try
                            End If
                        End If
                    Catch exRecurse As Exception
                        oLog.Append(vbCrLf & "  DERIVED SOURCE (recursive chain): failed on " & sNewFileName & sExt & " (" & exRecurse.Message & ")")
                    End Try
                End If
                ' Re-suppress the derive feature if it was suppressed before
                If bDeriveSuppressed Then
                    Try
                        If oSuppressedFeature IsNot Nothing Then
                            CType(oSuppressedFeature, Object).Suppressed = True
                        Else
                            Try
                                Dim oPartDefRS As PartComponentDefinition = oPartDoc.ComponentDefinition
                                If oPartDefRS.BaseComponent IsNot Nothing Then oPartDefRS.BaseComponent.SetActive(False)
                            Catch
                            End Try
                        End If
                    Catch
                    End Try
                End If
            Catch ex As Exception
                oLog.Append(vbCrLf & "FAILED to repoint to existing derived source: " & sNewFileName & sExt & " (" & ex.Message & ")")
            End Try

        Else
            ' Need to copy the source to the new name first.
            ' Branch on file type: Inventor-native files (.ipt, .iam, .ipn)
            ' can be opened and SaveAs'd through the Inventor API. All other
            ' types (.xlsx, .xls, .csv, .txt, .json, .xml and anything else
            ' we haven't specifically listed) are copied at OS level only -
            ' no Documents.Open, no SaveAs. This prevents Excel, AutoCAD or
            ' other applications being launched by Inventor's document open.
            '
            ' .dwg, .dxf, .stp, .step, .igs, .iges, .stl, .obj, .pdf,
            ' images etc. are skipped entirely - they can't be repointed
            ' through the Inventor file descriptor API in a meaningful way
            ' and their presence as referenced files is usually for visual
            ' reference only (embedded sketches, background images etc.).
            Dim sExtUpper As String = sExt.ToUpper()
            Dim bIsInventorNative As Boolean = (sExtUpper = ".IPT" OrElse sExtUpper = ".IAM" OrElse sExtUpper = ".IPN")
            Dim bIsFileCopyOnly As Boolean = (sExtUpper = ".XLSX" OrElse sExtUpper = ".XLS" OrElse
                                              sExtUpper = ".CSV" OrElse sExtUpper = ".TXT" OrElse
                                              sExtUpper = ".JSON" OrElse sExtUpper = ".XML")
            Dim bIsSkipped As Boolean = Not bIsInventorNative AndAlso Not bIsFileCopyOnly

            If bIsSkipped Then
                ' Non-processable file type - log and skip.
                oLog.Append(vbCrLf & "DERIVED SOURCE SKIPPED (non-processable type " & sExtUpper & "): " & sRefFileName & sExt & "  [used by " & System.IO.Path.GetFileName(oPartDoc.FullFileName) & "]")
                Continue For
            End If

            If bIsFileCopyOnly Then
                ' Excel, CSV, TXT etc. - File.Copy only, no Inventor API open/SaveAs.
                ' These are parameter tables or iLogic spreadsheets and can be
                ' copied directly. ReplaceReference updates the part's internal
                ' link to point at the new copy.
                Try
                    System.IO.Directory.CreateDirectory(System.IO.Path.GetDirectoryName(sNewFullName))
                Catch
                End Try
                Try
                    System.IO.File.Copy(sRefFullName, sNewFullName, False)
                    ' Clear read-only on the COPIED xlsx - Vault-checked-in sources
                    ' inherit the RO attribute on copy, showing as locked in Explorer.
                    Try
                        Dim oXlsxAttrs As System.IO.FileAttributes = System.IO.File.GetAttributes(sNewFullName)
                        If (oXlsxAttrs And System.IO.FileAttributes.ReadOnly) = System.IO.FileAttributes.ReadOnly Then
                            System.IO.File.SetAttributes(sNewFullName, oXlsxAttrs And Not System.IO.FileAttributes.ReadOnly)
                        End If
                    Catch
                    End Try
                    ' Clear read-only on the part before ReplaceReference.
                    Try
                        Dim oPartAttrsFC As System.IO.FileAttributes = System.IO.File.GetAttributes(oPartDoc.FullFileName)
                        If (oPartAttrsFC And System.IO.FileAttributes.ReadOnly) = System.IO.FileAttributes.ReadOnly Then
                            System.IO.File.SetAttributes(oPartDoc.FullFileName, oPartAttrsFC And Not System.IO.FileAttributes.ReadOnly)
                        End If
                    Catch
                    End Try
                    oFileDesc.ReplaceReference(sNewFullName)
                    oRenameMap(sRefFullName) = sNewFullName
                    iCount = iCount + 1
                    oLog.Append(vbCrLf & "DERIVED SOURCE" & IIf(bDeriveSuppressed, " (suppressed)", "") & ": " & sRefFileName & sExt & "   -->   " & sNewFileName & sExt & IIf(bRoutedToNonStd, "  (routed to Non Std Parts)", "") & "  [used by " & System.IO.Path.GetFileName(oPartDoc.FullFileName) & "]  [File.Copy - " & sExtUpper & "]")
                    bChanged = True
                Catch exFC As Exception
                    oLog.Append(vbCrLf & "FAILED to copy derived source (" & sExtUpper & "): " & sRefFileName & sExt & " (" & exFC.Message & ")")
                End Try
                Continue For
            End If

            ' Inventor-native file (.ipt / .iam / .ipn) - full open/SaveAs path.
            Try
                Dim oSourceDoc As Document = Nothing

                ' The source may already be open in the session (common for
                ' derived parts, even when not placed as an occurrence).
                Try
                    oSourceDoc = ThisApplication.Documents.ItemByName(sRefFullName)
                Catch
                    oSourceDoc = Nothing
                End Try

                If oSourceDoc Is Nothing Then
                    Try
                        System.IO.File.AppendAllText(sLogFilePath, "      " & DateTime.Now.ToString("HH:mm:ss.fff") & "  Opening derived source (not already loaded): " & sRefFullName & vbCrLf)
                    Catch
                    End Try
                    Dim bSourceDocOpenedHere As Boolean = False
                    oSourceDoc = OpenDocTracked(sRefFullName, bSourceDocOpenedHere)
                    Try
                        System.IO.File.AppendAllText(sLogFilePath, "      " & DateTime.Now.ToString("HH:mm:ss.fff") & "  Open finished." & vbCrLf)
                    Catch
                    End Try
                End If

                Try
                    System.IO.File.AppendAllText(sLogFilePath, "      " & DateTime.Now.ToString("HH:mm:ss.fff") & "  SaveAs starting (derived source): " & sRefFileName & sExt & "  ->  " & sNewFileName & sExt & vbCrLf)
                Catch
                End Try

                Dim bDerivedSaveAsOk As Boolean = False
                Try
                    oSourceDoc.SaveAs(sNewFullName, True)
                    bDerivedSaveAsOk = True
                    Try
                        System.IO.File.AppendAllText(sLogFilePath, "      " & DateTime.Now.ToString("HH:mm:ss.fff") & "  SaveAs finished." & vbCrLf)
                    Catch
                    End Try
                Catch exSaveAs As Exception
                    Try
                        System.IO.File.AppendAllText(sLogFilePath, "      " & DateTime.Now.ToString("HH:mm:ss.fff") & "  SaveAs threw (" & exSaveAs.Message & ") - will attempt File.Copy fallback." & vbCrLf)
                    Catch
                    End Try
                End Try

                If Not bDerivedSaveAsOk OrElse Not System.IO.File.Exists(sNewFullName) Then
                    System.IO.File.Copy(sRefFullName, sNewFullName, False)
                    Try
                        System.IO.File.AppendAllText(sLogFilePath, "      " & DateTime.Now.ToString("HH:mm:ss.fff") & "  File.Copy fallback succeeded (derived source)." & vbCrLf)
                    Catch
                    End Try
                End If

                ' Clear read-only on the part before ReplaceReference.
                ' File.Copy'd parts from Vault may be read-only, causing silent failure.
                Try
                    Dim oPartAttrs2 As System.IO.FileAttributes = System.IO.File.GetAttributes(oPartDoc.FullFileName)
                    If (oPartAttrs2 And System.IO.FileAttributes.ReadOnly) = System.IO.FileAttributes.ReadOnly Then
                        System.IO.File.SetAttributes(oPartDoc.FullFileName, oPartAttrs2 And Not System.IO.FileAttributes.ReadOnly)
                    End If
                Catch
                End Try

                oFileDesc.ReplaceReference(sNewFullName)

                oRenameMap(sRefFullName) = sNewFullName
                iCount = iCount + 1
                oLog.Append(vbCrLf & "DERIVED SOURCE " & sRefFileName & sExt & "   -->   " & sNewFileName & sExt & IIf(bRoutedToNonStd, "  (routed to Non Std Parts)", "") & "  [used by " & System.IO.Path.GetFileName(oPartDoc.FullFileName) & "]" & IIf(Not bDerivedSaveAsOk, "  [copied via File.Copy - re-run Mode 3 to fix internal references]", ""))
                bChanged = True

                ' Close the source doc if WE opened it (SaveCopyAs leaves original open)
                CloseIfOpenedHere(oSourceDoc, bSourceDocOpenedHere)

                ' RECURSIVE: chase grandparent derive chain - only if already open in session.
                Try
                    Dim oNewCopyDocR2 As Document = Nothing
                    Try : oNewCopyDocR2 = ThisApplication.Documents.ItemByName(sNewFullName) : Catch : oNewCopyDocR2 = Nothing : End Try
                    ' Only recurse if already open - never Documents.Open a cold file here
                    If oNewCopyDocR2 IsNot Nothing Then
                        If ProcessDerivedSource(oNewCopyDocR2, sFind, sReplace, bUseContainsMode, sTargetFolder, sTopAssemblyFullName, oLog, iCount, oRenameMap, sLogFilePath) Then
                            bChanged = True
                            Try : oNewCopyDocR2.Save2(False) : Catch : End Try
                        End If
                    End If
                Catch exRecurse2 As Exception
                    oLog.Append(vbCrLf & "  DERIVED SOURCE (recursive chain): failed on " & sNewFileName & sExt & " (" & exRecurse2.Message & ")")
                End Try

            Catch ex As Exception
                oLog.Append(vbCrLf & "FAILED to copy derived source: " & sRefFileName & sExt & " (" & ex.Message & ")")
                Try
                    System.IO.File.AppendAllText(sLogFilePath, "      " & DateTime.Now.ToString("HH:mm:ss.fff") & "  FAILED: " & ex.Message & vbCrLf)
                Catch
                End Try
            End Try
        End If

        ' --- DECISION LOG FLUSH: same reasoning as the main entry loop above. ---
        Try
            System.IO.File.WriteAllText(System.IO.Path.Combine(System.IO.Path.GetDirectoryName(sLogFilePath), System.IO.Path.GetFileNameWithoutExtension(sLogFilePath) & "_Decisions.txt"), oLog.ToString())
        Catch
        End Try

    Next

    ' RE-SUPPRESS: restore suppressed feature state if temporarily unsuppressed above
    If oPreUnsuppressedFeature IsNot Nothing Then
        Try
            CType(oPreUnsuppressedFeature, Object).Suppressed = True
            oLog.Append(vbCrLf & "  DERIVE RE-SUPPRESS: restored suppressed feature state in " & System.IO.Path.GetFileName(oPartDoc.FullFileName))
        Catch
            Try
                If oPartDoc.DocumentType = kPartDocumentObject Then
                    Dim oRSPartDef As PartComponentDefinition = oPartDoc.ComponentDefinition
                    If oRSPartDef.BaseComponent IsNot Nothing Then oRSPartDef.BaseComponent.SetActive(False)
                End If
            Catch
            End Try
        End Try
        oPreUnsuppressedFeature = Nothing
    End If

    ' RE-SUPPRESS LINKS: restore SuppressLinkToFile on any derived components
    ' we temporarily unsuppressed in the pre-pass (so geometry stays static again).
    If oPreUnsuppressedLinkComps.Count > 0 Then
        For Each oLinkComp As Object In oPreUnsuppressedLinkComps
            Try
                oLinkComp.SuppressLinkToFile = True
                Dim sLnName As String = "?"
                Try : sLnName = oLinkComp.Name : Catch : End Try
                oLog.Append(vbCrLf & "  DERIVE RE-SUPPRESS LINK: restored suppressed link on '" & sLnName & "' in " & System.IO.Path.GetFileName(oPartDoc.FullFileName))
            Catch
            End Try
        Next
        oPreUnsuppressedLinkComps.Clear()
    End If

    ' --- FIX C: BaseComponent derive path -----------------------------------
    ' File.ReferencedFileDescriptors only covers file-level references. It
    ' does NOT cover the Inventor "Derive Component" / "Derive Part"
    ' relationship stored in PartComponentDefinition.BaseComponent. When a
    ' part derives from another Inventor part that way, the source is
    ' accessible only via oPartDef.BaseComponent.Document - completely
    ' invisible to the loop above. This block handles that second path.
    Try
        Dim oPartDef As PartComponentDefinition = oPartDoc.ComponentDefinition
        If oPartDef.BaseComponent IsNot Nothing Then
            Dim oBaseDoc As Document = Nothing
            Dim sBaseFullName As String = ""
            Try
                oBaseDoc = oPartDef.BaseComponent.Document
                sBaseFullName = oBaseDoc.FullFileName
            Catch
                sBaseFullName = ""
            End Try

            If sBaseFullName <> "" Then
                ' Already handled this run via oRenameMap?
                If oRenameMap.ContainsKey(sBaseFullName) Then
                    ' The base source was renamed - Inventor's derive link updates
                    ' automatically when the document is repointed; if it hasn't,
                    ' log it for awareness. Nothing more to do here since
                    ' the occurrence-level Replace() already repointed the file.
                    oLog.Append(vbCrLf & "  BASE COMPONENT (derive): source already repointed this run: " & System.IO.Path.GetFileName(sBaseFullName) & "  -->  " & System.IO.Path.GetFileName(oRenameMap(sBaseFullName)) & "  [part: " & System.IO.Path.GetFileName(oPartDoc.FullFileName) & "]")
                ElseIf Not IsInExcludedFolder(sBaseFullName) Then
                    Dim sBaseNameNoExt As String = System.IO.Path.GetFileNameWithoutExtension(sBaseFullName)
                    Dim sBaseExt As String = System.IO.Path.GetExtension(sBaseFullName)
                    Dim bBaseMatch As Boolean
                    If bUseContainsMode Then
                        bBaseMatch = sBaseNameNoExt.ToUpper().Contains(sFind.ToUpper())
                    Else
                        bBaseMatch = sBaseNameNoExt.ToUpper().StartsWith(sFind.ToUpper())
                    End If

                    If bBaseMatch Then
                        Dim sBaseNewName As String
                        If bUseContainsMode Then
                            sBaseNewName = ReplaceAllCaseInsensitive(sBaseNameNoExt, sFind, sReplace)
                        Else
                            sBaseNewName = sReplace & sBaseNameNoExt.Substring(sFind.Length)
                        End If
                        Dim sBaseNewFull As String = System.IO.Path.Combine(GetEffectiveTargetFolder(sBaseFullName, sTargetFolder), sBaseNewName & sBaseExt)

                        If String.Compare(sBaseNewFull, sTopAssemblyFullName, True) = 0 Then
                            oLog.Append(vbCrLf & "  BASE COMPONENT SAFETY SKIP: new name would collide with top assembly.")
                        ElseIf System.IO.File.Exists(sBaseNewFull) Then
                            ' Already on disk - just repoint
                            oRenameMap(sBaseFullName) = sBaseNewFull
                            iCount = iCount + 1
                            bChanged = True
                            oLog.Append(vbCrLf & "  BASE COMPONENT (derive) repointed to existing copy: " & sBaseNameNoExt & sBaseExt & "  -->  " & sBaseNewName & sBaseExt & "  [part: " & System.IO.Path.GetFileName(oPartDoc.FullFileName) & "]")
                        Else
                            ' Need to copy the base source to the new name
                            Dim bBaseSaveAsOk As Boolean = False
                            Dim bBaseOpenedHere As Boolean = False
                            Try
                                System.IO.File.AppendAllText(sLogFilePath, "      " & DateTime.Now.ToString("HH:mm:ss.fff") & "  BASE COMPONENT SaveAs starting: " & sBaseNameNoExt & sBaseExt & "  ->  " & sBaseNewName & sBaseExt & vbCrLf)
                            Catch
                            End Try
                            Try
                                If oBaseDoc Is Nothing Then
                                    Try
                                        oBaseDoc = ThisApplication.Documents.ItemByName(sBaseFullName)
                                    Catch
                                        oBaseDoc = Nothing
                                    End Try
                                    If oBaseDoc Is Nothing Then oBaseDoc = OpenDocTracked(sBaseFullName, bBaseOpenedHere)
                                End If
                                If oBaseDoc Is Nothing Then Throw New Exception("could not open base component")
                                oBaseDoc.SaveAs(sBaseNewFull, True)
                                bBaseSaveAsOk = True
                                Try
                                    System.IO.File.AppendAllText(sLogFilePath, "      " & DateTime.Now.ToString("HH:mm:ss.fff") & "  BASE COMPONENT SaveAs finished." & vbCrLf)
                                Catch
                                End Try
                            Catch exBSaveAs As Exception
                                Try
                                    System.IO.File.AppendAllText(sLogFilePath, "      " & DateTime.Now.ToString("HH:mm:ss.fff") & "  BASE COMPONENT SaveAs threw (" & exBSaveAs.Message & ") - File.Copy fallback." & vbCrLf)
                                Catch
                                End Try
                            End Try
                            If Not bBaseSaveAsOk OrElse Not System.IO.File.Exists(sBaseNewFull) Then
                                Try
                                    System.IO.File.Copy(sBaseFullName, sBaseNewFull, False)
                                    Try
                                        System.IO.File.AppendAllText(sLogFilePath, "      " & DateTime.Now.ToString("HH:mm:ss.fff") & "  BASE COMPONENT File.Copy fallback succeeded." & vbCrLf)
                                    Catch
                                    End Try
                                Catch exBCopy As Exception
                                    oLog.Append(vbCrLf & "  BASE COMPONENT copy FAILED: " & sBaseNameNoExt & sBaseExt & " (" & exBCopy.Message & ")")
                                End Try
                            End If
                            ' SaveAs(..., True) is a copy - the source is not used again here
                            CloseIfOpenedHere(oBaseDoc, bBaseOpenedHere)
                            If System.IO.File.Exists(sBaseNewFull) Then
                                oRenameMap(sBaseFullName) = sBaseNewFull
                                iCount = iCount + 1
                                bChanged = True
                                oLog.Append(vbCrLf & "  BASE COMPONENT (derive) copied and noted: " & sBaseNameNoExt & sBaseExt & "  -->  " & sBaseNewName & sBaseExt & "  [part: " & System.IO.Path.GetFileName(oPartDoc.FullFileName) & "]" & IIf(Not bBaseSaveAsOk, "  [File.Copy - re-run Mode 3 to fix internal refs]", ""))
            ' NOTE: Inventor updates the derive link automatically when the base
            ' document is renamed/repointed at the session level. We do not need
            ' to call ReplaceReference here - the BaseComponent link is managed
            ' by Inventor internally once the document object is updated.
                            End If
                        End If
                    End If
                End If
            End If
        End If
    Catch exBase As Exception
        ' Suppress version-not-supported errors ("member not found" / "not found")
        ' which occur on Inventor builds that don't expose BaseComponent.
        If Not exBase.Message.ToUpper().Contains("MEMBER") AndAlso _
           Not exBase.Message.ToUpper().Contains("NOT FOUND") Then
            oLog.Append(vbCrLf & "  BASE COMPONENT check failed in " & System.IO.Path.GetFileName(oPartDoc.FullFileName) & ": " & exBase.Message)
        End If
    End Try

    Return bChanged

End Function


' ---------------------------------------------------------------------
' MODE 5 - VERIFY ONLY
' Read-only scan of the full assembly tree. Reports every occurrence
' that still references a file outside the target folder, grouped by
' type (part, assembly, FG package, BC assembly, xlsx param table,
' derived source). No files are copied, renamed, or saved.
' ---------------------------------------------------------------------
Sub RunVerifyOnlyPass(oAsmDoc As AssemblyDocument, sTargetFolder As String, _
    oLog As System.Text.StringBuilder, ByRef iOldRefs As Integer, sLogFilePath As String)

    Dim oSeen As New System.Collections.Generic.HashSet(Of String)(StringComparer.OrdinalIgnoreCase)
    Dim sDecPath As String = System.IO.Path.Combine(System.IO.Path.GetDirectoryName(sLogFilePath), _
        System.IO.Path.GetFileNameWithoutExtension(sLogFilePath) & "_Decisions.txt")

    oLog.Append("MODE 5 - VERIFY ONLY" & vbCrLf)
    oLog.Append("Top assembly: " & oAsmDoc.FullFileName & vbCrLf)
    oLog.Append("Target folder: " & sTargetFolder & vbCrLf & vbCrLf)

    ' Walk every referenced document
    For Each oRefDoc As Document In oAsmDoc.AllReferencedDocuments
        If oRefDoc.DocumentType <> kPartDocumentObject AndAlso _
           oRefDoc.DocumentType <> kAssemblyDocumentObject Then Continue For
        Dim sFullName As String = ""
        Try : sFullName = oRefDoc.FullFileName : Catch : Continue For : End Try
        If Trim(sFullName) = "" OrElse sFullName.Contains("*") Then Continue For
        If IsInExcludedFolder(sFullName) Then Continue For
        If IsContentCenterMember(oRefDoc) Then Continue For
        If IsSyntheticPatternMemberName(sFullName) Then Continue For
        If oSeen.Contains(sFullName) Then Continue For
        oSeen.Add(sFullName)

        ' Is it outside the target folder?
        ' Skip excluded files (Vault library, Content Center, standard folder) -
        ' these are intentionally left in their original location and are not
        ' fixable by Mode 4 or the non-std rule, so don't report them as issues.
        If Not IsDocSafeToMutate(sFullName, sTargetFolder, oAsmDoc.FullFileName) Then
            ' Files in excluded folders or flagged as Content Center are intentionally
            ' left in their source location - tag as EXCLUDED, not as actionable.
            If IsInExcludedFolder(sFullName) OrElse IsContentCenterMember(oRefDoc) Then
                oLog.Append(vbCrLf & "[EXCLUDED - library/CC] " & System.IO.Path.GetFileName(sFullName))
                Continue For
            End If
            iOldRefs = iOldRefs + 1
            Dim sType As String = IIf(oRefDoc.DocumentType = kAssemblyDocumentObject, "ASM", "IPT")
            If oRefDoc.DocumentType = kAssemblyDocumentObject Then
                If IsBoltedConnectionAssembly(oRefDoc.ComponentDefinition) Then
                    sType = "BC-ASM"
                ElseIf IsFrameGeneratorAssembly(oRefDoc.ComponentDefinition, sFullName) Then
                    sType = "FG-ASM"
                End If
            End If
            oLog.Append(vbCrLf & "[" & sType & "] " & System.IO.Path.GetFileName(sFullName))
            oLog.Append(vbCrLf & "       " & sFullName)
        End If

        ' Check param table links inside this document
        Try
            Dim oTbls As Object = oRefDoc.ComponentDefinition.Parameters.DerivedParameterTables
            If oTbls IsNot Nothing Then
                For i As Integer = 1 To oTbls.Count
                    Try
                        Dim sRef As String = ""
                        Try : sRef = oTbls.Item(i).ReferencedDocumentDescriptor.FullDocumentName : Catch : End Try
                        If sRef <> "" AndAlso Not IsInExcludedFolder(sRef) Then
                            Dim sRefFolder As String = System.IO.Path.GetDirectoryName(sRef)
                            If Not sRefFolder.ToUpper().StartsWith(sTargetFolder.ToUpper()) Then
                                iOldRefs = iOldRefs + 1
                                oLog.Append(vbCrLf & "[PARAM-TBL] " & System.IO.Path.GetFileName(sRef))
                                oLog.Append(vbCrLf & "       in: " & System.IO.Path.GetFileName(sFullName))
                            End If
                        End If
                    Catch
                    End Try
                Next
            End If
        Catch
        End Try

        ' Check derive sources (file descriptors)
        If oRefDoc.DocumentType = kPartDocumentObject Then
            Try
                For Each oFD As FileDescriptor In oRefDoc.File.ReferencedFileDescriptors
                    Try
                        Dim sFDFull As String = ""
                        Try : sFDFull = oFD.FullFileName : Catch : Continue For : End Try
                        If sFDFull = "" OrElse IsInExcludedFolder(sFDFull) Then Continue For
                        Dim sFDExt As String = System.IO.Path.GetExtension(sFDFull).ToUpper()
                        If sFDExt <> ".IPT" AndAlso sFDExt <> ".IAM" AndAlso sFDExt <> ".XLSX" AndAlso sFDExt <> ".XLS" Then Continue For
                        If Not System.IO.Path.GetDirectoryName(sFDFull).ToUpper().StartsWith(sTargetFolder.ToUpper()) Then
                            If Not oSeen.Contains("FD:" & sFDFull) Then
                                oSeen.Add("FD:" & sFDFull)
                                iOldRefs = iOldRefs + 1
                                oLog.Append(vbCrLf & "[DERIVED] " & System.IO.Path.GetFileName(sFDFull))
                                oLog.Append(vbCrLf & "       in: " & System.IO.Path.GetFileName(sFullName))
                            End If
                        End If
                    Catch
                    End Try
                Next
            Catch
            End Try
        End If

        ' Flush to decisions log after each document
        Try : System.IO.File.WriteAllText(sDecPath, oLog.ToString()) : Catch : End Try
    Next

    ' Also check the top assembly's own param tables
    Try
        Dim oTopTbls As Object = oAsmDoc.ComponentDefinition.Parameters.DerivedParameterTables
        If oTopTbls IsNot Nothing Then
            For i As Integer = 1 To oTopTbls.Count
                Try
                    Dim sRef As String = ""
                    Try : sRef = oTopTbls.Item(i).ReferencedDocumentDescriptor.FullDocumentName : Catch : End Try
                    If sRef <> "" AndAlso Not IsInExcludedFolder(sRef) Then
                        If Not System.IO.Path.GetDirectoryName(sRef).ToUpper().StartsWith(sTargetFolder.ToUpper()) Then
                            iOldRefs = iOldRefs + 1
                            oLog.Append(vbCrLf & "[PARAM-TBL] " & System.IO.Path.GetFileName(sRef))
                            oLog.Append(vbCrLf & "       in: " & System.IO.Path.GetFileName(oAsmDoc.FullFileName) & " (top assembly)")
                        End If
                    End If
                Catch
                End Try
            Next
        End If
    Catch
    End Try

    If iOldRefs = 0 Then
        oLog.Append(vbCrLf & "RESULT: CLEAN - no actionable old-prefix references found.")
    Else
        oLog.Append(vbCrLf & vbCrLf & "RESULT: " & iOldRefs & " reference(s) outside the target folder.")
        oLog.Append(vbCrLf & "  [IPT]/[ASM] = files to fix with Mode 4 or non-std rule")
        oLog.Append(vbCrLf & "  [PARAM-TBL]/[DERIVED] = internal links (FG skeleton or derive sources)")
        oLog.Append(vbCrLf & "  Standard fasteners/hardware in source folders are expected and cannot be auto-fixed.")
    End If
    Try : System.IO.File.WriteAllText(sDecPath, oLog.ToString()) : Catch : End Try

End Sub


' ---------------------------------------------------------------------
' MODE 2 PRE-PASS: ORPHAN SWEEP
' Collects all files referenced by the assembly tree, then scans the
' target folder on disk and removes any .ipt/.iam files that are NOT
' referenced. These orphans accumulate from previous partial runs and
' cause false collisions during Mode 2 rename passes.
' SAFETY: only removes files inside sTargetFolder. Never touches the
' original source project folders.
' ---------------------------------------------------------------------
Sub RunOrphanSweepPass(oAsmDoc As AssemblyDocument, sTargetFolder As String, _
    sTopAssemblyFullName As String, sFind As String, sReplace As String, _
    oLog As System.Text.StringBuilder, ByRef iRemoved As Integer, ByRef iSkipped As Integer, sLogFilePath As String)

    ' Build set of all files referenced by the assembly in its CURRENT state.
    ' NOTE: Inventor resolves references at load time - if a file was renamed
    ' on disk from a previous run, Inventor may have resolved to the new name
    ' already. We collect both the resolved paths AND their on-disk actual names.
    Dim oReferenced As New System.Collections.Generic.HashSet(Of String)(StringComparer.OrdinalIgnoreCase)
    oReferenced.Add(sTopAssemblyFullName.ToUpper())
    For Each oRefDoc As Document In oAsmDoc.AllReferencedDocuments
        Try
            Dim sRef As String = oRefDoc.FullFileName
            If sRef <> "" Then oReferenced.Add(sRef.ToUpper())
        Catch
        End Try
    Next

    ' CRITICAL SAFETY: also protect files that are rename-variants of referenced
    ' files from a previous partial Mode 2 run. A file is a variant of a referenced
    ' file if replacing sReplace back with sFind in its name produces a path that
    ' IS in the referenced set. e.g. if Find='_ReferenceCopy', Replace='_Duplicate':
    ' 'V0-01_Duplicate_MiR.iam' -> replace '_Duplicate' with '_ReferenceCopy' ->
    ' 'V0-01_ReferenceCopy_MiR.iam' -> IS referenced -> PROTECT this file.
    ' This prevents sweeping files created by a previous partial Mode 2 run.
    Dim sReplaceUpper As String = sReplace.ToUpper()
    Dim sFindUpper As String = sFind.ToUpper()

    ' Walk all .ipt and .iam files in the target folder tree
    Dim sTargetUpper As String = sTargetFolder.ToUpper()
    Dim oAllFiles As String() = System.IO.Directory.GetFiles(sTargetFolder, "*.*", System.IO.SearchOption.AllDirectories)
    For Each sFilePath As String In oAllFiles
        Try
            Dim sExt As String = System.IO.Path.GetExtension(sFilePath).ToUpper()
            If sExt <> ".IPT" AndAlso sExt <> ".IAM" Then Continue For

            ' Safety: must be inside target folder
            If Not sFilePath.ToUpper().StartsWith(sTargetUpper) Then Continue For

            ' Never remove the top assembly itself
            If String.Compare(sFilePath, sTopAssemblyFullName, True) = 0 Then Continue For

            ' Protected: directly referenced
            If oReferenced.Contains(sFilePath.ToUpper()) Then
                iSkipped = iSkipped + 1
                Continue For
            End If

            ' Protected: reverse-transform check
            ' If replacing sReplace->sFind in this file's name gives a referenced path,
            ' this file is a variant from a previous partial run - protect it.
            Dim bProtected As Boolean = False
            If sReplaceUpper <> "" AndAlso sFilePath.ToUpper().Contains(sReplaceUpper) Then
                Dim sReversed As String = ReplaceAllCaseInsensitive(sFilePath, sReplace, sFind)
                If oReferenced.Contains(sReversed.ToUpper()) Then
                    bProtected = True
                End If
            End If
            If bProtected Then
                iSkipped = iSkipped + 1
                Continue For
            End If

            ' Genuine orphan - not referenced and not a variant of anything referenced
            Try
                Dim oAttrs As System.IO.FileAttributes = System.IO.File.GetAttributes(sFilePath)
                If (oAttrs And System.IO.FileAttributes.ReadOnly) = System.IO.FileAttributes.ReadOnly Then
                    System.IO.File.SetAttributes(sFilePath, oAttrs And Not System.IO.FileAttributes.ReadOnly)
                End If
                System.IO.File.Delete(sFilePath)
                iRemoved = iRemoved + 1
                oLog.Append(vbCrLf & "ORPHAN REMOVED: " & System.IO.Path.GetFileName(sFilePath))
                Try : System.IO.File.AppendAllText(sLogFilePath, "ORPHAN REMOVED: " & sFilePath & vbCrLf) : Catch : End Try
            Catch exDel As Exception
                oLog.Append(vbCrLf & "ORPHAN DELETE FAILED: " & System.IO.Path.GetFileName(sFilePath) & " (" & exDel.Message & ")")
                iSkipped = iSkipped + 1
            End Try
        Catch
        End Try
    Next

End Sub


Function ScanPrefixes(oAsmDoc As AssemblyDocument) As System.Collections.Generic.List(Of String)

    ' Map: token -> set of distinct filenames carrying it
    Dim oTokenFiles As New System.Collections.Generic.Dictionary(Of String, System.Collections.Generic.HashSet(Of String))(StringComparer.OrdinalIgnoreCase)

    ' Build a deduplicated set of all file paths in the assembly tree.
    ' We work with paths (strings) rather than COM Document objects so that
    ' Vault's COM interception of checked-in files cannot block us.
    '
    ' Four-tier strategy — each tier only runs if the previous yielded nothing:
    '
    ' Tier 0 — AllOccurrences path walk (PREFERRED, Vault-proof):
    '   ComponentDefinition.AllOccurrences is an in-memory occurrence tree
    '   already loaded when the GA was opened. Reading FullDocumentName off
    '   each occurrence's ReferencedFileDescriptor is a pure string property
    '   lookup — no COM document resolution, no Vault hook. This is the
    '   correct approach for a checked-in Vault assembly.
    '
    ' Tier 1 — AllReferencedDocuments (works for unlocked/local assemblies).
    ' Tier 2 — BFS via ReferencedDocuments one level at a time.
    ' Tier 3 — ThisApplication.Documents session scan (Vault-proof fallback).

    Dim oAllPaths As New System.Collections.Generic.HashSet(Of String)(StringComparer.OrdinalIgnoreCase)

    ' Always include the top assembly's own path first.
    Try : oAllPaths.Add(oAsmDoc.FullFileName) : Catch : End Try

    ' --- Tier 0: occurrence tree path walk ---
    Dim iTier0Count As Integer = 0
    Try
        For Each oOcc As ComponentOccurrence In oAsmDoc.ComponentDefinition.AllOccurrences
            Try
                Dim sOccPath As String = oOcc.ReferencedFileDescriptor.FullDocumentName
                If Trim(sOccPath) <> "" AndAlso Not sOccPath.Contains("*") Then
                    oAllPaths.Add(sOccPath)
                    iTier0Count += 1
                End If
            Catch
            End Try
        Next
    Catch
    End Try

    ' --- Tier 1: AllReferencedDocuments (adds Document objects for param-table scan below) ---
    Dim oAllDocs As New System.Collections.Generic.List(Of Document)
    If iTier0Count = 0 Then
        Try
            For Each oD As Document In oAsmDoc.AllReferencedDocuments
                oAllDocs.Add(oD)
                Try : oAllPaths.Add(oD.FullFileName) : Catch : End Try
            Next
        Catch
        End Try
    End If

    ' --- Tier 2: BFS via ReferencedDocuments ---
    If iTier0Count = 0 AndAlso oAllDocs.Count = 0 Then
        Dim oQueue As New System.Collections.Generic.Queue(Of Document)
        Dim oVisitedScan As New System.Collections.Generic.HashSet(Of String)(StringComparer.OrdinalIgnoreCase)
        oQueue.Enqueue(oAsmDoc)
        While oQueue.Count > 0
            Dim oCurrent As Document = oQueue.Dequeue()
            Try
                For Each oChild As Document In oCurrent.ReferencedDocuments
                    Try
                        Dim sChildPath As String = oChild.FullFileName
                        If Not oVisitedScan.Contains(sChildPath) Then
                            oVisitedScan.Add(sChildPath)
                            oAllDocs.Add(oChild)
                            oAllPaths.Add(sChildPath)
                            If oChild.DocumentType = kAssemblyDocumentObject Then oQueue.Enqueue(oChild)
                        End If
                    Catch
                    End Try
                Next
            Catch
            End Try
        End While
    End If

    ' --- Tier 3: session document scan ---
    If iTier0Count = 0 AndAlso oAllDocs.Count = 0 Then
        Dim sTopDrive As String = ""
        Try
            sTopDrive = System.IO.Path.GetPathRoot(oAsmDoc.FullFileName).ToUpper()   ' e.g. "C:\"
        Catch
        End Try
        Try
            For Each oSessionDoc As Document In ThisApplication.Documents
                Try
                    If oSessionDoc.DocumentType <> kPartDocumentObject AndAlso _
                       oSessionDoc.DocumentType <> kAssemblyDocumentObject Then Continue For
                    Dim sPath As String = oSessionDoc.FullFileName
                    If sTopDrive = "" OrElse sPath.ToUpper().StartsWith(sTopDrive) Then
                        oAllDocs.Add(oSessionDoc)
                        oAllPaths.Add(sPath)
                    End If
                Catch
                End Try
            Next
        Catch
        End Try
    End If

    ' Token extraction — iterate paths (works regardless of which tier populated them).
    For Each sFullName As String In oAllPaths
        Dim sExt As String = System.IO.Path.GetExtension(sFullName).ToLower()
        If sExt <> ".iam" AndAlso sExt <> ".ipt" Then Continue For
        If IsInExcludedFolder(sFullName) Then Continue For
        If IsSyntheticPatternMemberName(sFullName) Then Continue For

        Dim sFileOnly As String = System.IO.Path.GetFileNameWithoutExtension(sFullName)
        If sFileOnly = "" Then Continue For
        If Not sFileOnly.ToUpper().StartsWith("P") Then Continue For

        ' Extract token: everything up to first "-" or "_"
        Dim iDash As Integer = sFileOnly.IndexOf("-")
        Dim iUnder As Integer = sFileOnly.IndexOf("_")
        Dim iSep As Integer = -1
        If iDash >= 0 AndAlso iUnder >= 0 Then
            iSep = Math.Min(iDash, iUnder)
        ElseIf iDash >= 0 Then
            iSep = iDash
        ElseIf iUnder >= 0 Then
            iSep = iUnder
        End If

        Dim sToken As String
        If iSep > 0 Then
            sToken = sFileOnly.Substring(0, iSep).ToUpper()
        Else
            sToken = sFileOnly.ToUpper()
        End If

        If sToken.Length < 2 Then Continue For
        ' GUARD: only accept real project-code prefixes (PJ + exactly 5 digits).
        ' Without this, product-description filenames like "PARKER MALE TAPER THREAD 1"
        ' or "PJ00205 DN400 SLIP ON FLANGE" are extracted as prefix tokens and cause
        ' catastrophic renames (e.g. "Parker Male Taper Thread 1_2.ipt" → "PJ00205_2.ipt").
        If Not System.Text.RegularExpressions.Regex.IsMatch(sToken, "^PJ\d{5}$") Then Continue For

        If Not oTokenFiles.ContainsKey(sToken) Then
            oTokenFiles(sToken) = New System.Collections.Generic.HashSet(Of String)(StringComparer.OrdinalIgnoreCase)
        End If
        oTokenFiles(sToken).Add(sFullName)
    Next

    ' Scan param tables and file descriptors of every document
    ' to expose old prefix xlsx links invisible to the file scan.
    ' Re-use oAllDocs built above (already covers the full tree via either path).
    For Each oRefDoc2 As Document In oAllDocs
        If oRefDoc2.DocumentType <> kPartDocumentObject AndAlso _
           oRefDoc2.DocumentType <> kAssemblyDocumentObject Then Continue For
        Try
            If IsContentCenterMember(oRefDoc2) Then Continue For
        Catch
        End Try
        Dim oScanCols As New System.Collections.Generic.List(Of Object)
        Try
            Dim oDPT As Object = oRefDoc2.ComponentDefinition.Parameters.DerivedParameterTables
            If oDPT IsNot Nothing AndAlso oDPT.Count > 0 Then oScanCols.Add(oDPT)
        Catch : End Try
        If oRefDoc2.DocumentType = kAssemblyDocumentObject Then
            Try
                Dim oPS As Object = oRefDoc2.ComponentDefinition.Parameters.ParameterSets
                If oPS IsNot Nothing AndAlso oPS.Count > 0 Then oScanCols.Add(oPS)
            Catch : End Try
        End If
        For Each oTbls As Object In oScanCols
            Try
                For i As Integer = 1 To oTbls.Count
                    Try
                        Dim sRF As String = ""
                        Try : sRF = oTbls.Item(i).ReferencedDocumentDescriptor.FullDocumentName : Catch : End Try
                        If Trim(sRF) = "" OrElse IsInExcludedFolder(sRF) Then Continue For
                        Dim sRFN As String = System.IO.Path.GetFileNameWithoutExtension(sRF)
                        If Not sRFN.ToUpper().StartsWith("P") Then Continue For
                        Dim iSR As Integer = sRFN.IndexOf("-")
                        If iSR < 2 Then Continue For
                        Dim sTR As String = sRFN.Substring(0, iSR).ToUpper()
                        If sTR.Length >= 2 Then
                            If Not oTokenFiles.ContainsKey(sTR) Then oTokenFiles(sTR) = New System.Collections.Generic.HashSet(Of String)(StringComparer.OrdinalIgnoreCase)
                            oTokenFiles(sTR).Add(sRF)
                        End If
                    Catch : End Try
                Next
            Catch : End Try
        Next
        Try
            For Each oFD2 As FileDescriptor In oRefDoc2.File.ReferencedFileDescriptors
                Try
                    Dim sFD As String = ""
                    Try : sFD = oFD2.FullFileName : Catch : End Try
                    If Trim(sFD) = "" OrElse IsInExcludedFolder(sFD) Then Continue For
                    Dim sFDN As String = System.IO.Path.GetFileNameWithoutExtension(sFD)
                    If Not sFDN.ToUpper().StartsWith("P") Then Continue For
                    Dim iSFD As Integer = sFDN.IndexOf("-")
                    If iSFD < 2 Then Continue For
                    Dim sTFD As String = sFDN.Substring(0, iSFD).ToUpper()
                    If sTFD.Length >= 2 Then
                        If Not oTokenFiles.ContainsKey(sTFD) Then oTokenFiles(sTFD) = New System.Collections.Generic.HashSet(Of String)(StringComparer.OrdinalIgnoreCase)
                        oTokenFiles(sTFD).Add(sFD)
                    End If
                Catch : End Try
            Next
        Catch : End Try
    Next

    ' Also check the top assembly itself
    Try
        Dim sTopFile As String = System.IO.Path.GetFileNameWithoutExtension(oAsmDoc.FullFileName)
        If sTopFile.ToUpper().StartsWith("P") Then
            Dim idxD As Integer = sTopFile.IndexOf("-")
            Dim idxU As Integer = sTopFile.IndexOf("_")
            Dim idxSep As Integer = -1
            If idxD >= 0 AndAlso idxU >= 0 Then
                idxSep = Math.Min(idxD, idxU)
            ElseIf idxD >= 0 Then
                idxSep = idxD
            ElseIf idxU >= 0 Then
                idxSep = idxU
            End If
            Dim sTok As String
            If idxSep > 0 Then
                sTok = sTopFile.Substring(0, idxSep).ToUpper()
            Else
                sTok = sTopFile.ToUpper()
            End If
            If sTok.Length >= 2 Then
                If Not oTokenFiles.ContainsKey(sTok) Then
                    oTokenFiles(sTok) = New System.Collections.Generic.HashSet(Of String)(StringComparer.OrdinalIgnoreCase)
                End If
                oTokenFiles(sTok).Add(oAsmDoc.FullFileName)
            End If
        End If
    Catch
    End Try

    ' Sort tokens alphabetically and format as "TOKEN|COUNT"
    Dim oSorted As New System.Collections.Generic.List(Of String)
    For Each kvp As System.Collections.Generic.KeyValuePair(Of String, System.Collections.Generic.HashSet(Of String)) In oTokenFiles
        oSorted.Add(kvp.Key & "|" & kvp.Value.Count.ToString())
    Next
    oSorted.Sort()
    Return oSorted

End Function


Function ShowBatchSelectionForm(oTokenList As System.Collections.Generic.List(Of String), ByRef oResult As RenameModeChoice) As Boolean

    If oTokenList.Count = 0 Then
        MessageBox.Show("No P-prefixed project files found in this assembly tree." & vbCrLf & "Nothing to batch-replace.", "Mode 4 - No P-Prefixes Found")
        Return False
    End If

    Dim oForm As New Form()
    oForm.Text = "Mode 4 - Batch P-Prefix Swap"
    oForm.StartPosition = FormStartPosition.CenterScreen
    oForm.TopMost = True
    oForm.FormBorderStyle = FormBorderStyle.FixedDialog
    oForm.MinimizeBox = False
    oForm.MaximizeBox = False
    oForm.Width = 540
    ' Height grows with the number of tokens, capped at 680
    Dim iRowHeight As Integer = 26
    Dim iListTop As Integer = 100
    Dim iListHeight As Integer = Math.Min(oTokenList.Count * iRowHeight + 10, 420)
    oForm.Height = Math.Min(iListTop + iListHeight + 160, 680)

    Dim oLblTitle As New Label()
    oLblTitle.Text = "The following P-prefixed project numbers were found in the tree." & vbCrLf & _
                     "Tick the ones you want to replace, then enter the new project number."
    oLblTitle.Left = 15
    oLblTitle.Top = 12
    oLblTitle.Width = 500
    oLblTitle.Height = 40
    oForm.Controls.Add(oLblTitle)

    ' Tick-all / Untick-all buttons
    Dim oBtnAll As New Button()
    oBtnAll.Text = "Select All"
    oBtnAll.Left = 15
    oBtnAll.Top = 58
    oBtnAll.Width = 90
    oForm.Controls.Add(oBtnAll)

    Dim oBtnNone As New Button()
    oBtnNone.Text = "Clear All"
    oBtnNone.Left = 115
    oBtnNone.Top = 58
    oBtnNone.Width = 90
    oForm.Controls.Add(oBtnNone)

    ' Scrollable panel for the checkboxes
    Dim oPanel As New Panel()
    oPanel.Left = 15
    oPanel.Top = iListTop
    oPanel.Width = 500
    oPanel.Height = iListHeight
    oPanel.AutoScroll = True
    oPanel.BorderStyle = BorderStyle.FixedSingle
    oForm.Controls.Add(oPanel)

    ' One checkbox per token
    Dim oCheckboxes As New System.Collections.Generic.List(Of CheckBox)
    Dim iY As Integer = 5
    For Each sEntry As String In oTokenList
        Dim sParts() As String = sEntry.Split(New Char() {"|"c})
        Dim sToken As String = sParts(0)
        Dim sCount As String
        If sParts.Length > 1 Then
            sCount = sParts(1)
        Else
            sCount = "?"
        End If
        Dim oChk As New CheckBox()
        oChk.Text = sToken & "   (" & sCount & " file(s))"
        oChk.Left = 6
        oChk.Top = iY
        oChk.Width = 470
        oChk.Checked = True  ' default: all selected
        oChk.Tag = Trim(sToken)    ' store the trimmed token for retrieval
        oPanel.Controls.Add(oChk)
        oCheckboxes.Add(oChk)
        iY = iY + iRowHeight
    Next

    AddHandler oBtnAll.Click, Sub(s, e)
        For Each cb As CheckBox In oCheckboxes
            cb.Checked = True
        Next
    End Sub
    AddHandler oBtnNone.Click, Sub(s, e)
        For Each cb As CheckBox In oCheckboxes
            cb.Checked = False
        Next
    End Sub

    ' New project number input
    Dim iControlTop As Integer = iListTop + iListHeight + 12
    Dim oLblNew As New Label()
    oLblNew.Text = "Replace selected prefix(es) with new project number:"
    oLblNew.Left = 15
    oLblNew.Top = iControlTop
    oLblNew.Width = 500
    oForm.Controls.Add(oLblNew)

    Dim oTxtNew As New System.Windows.Forms.TextBox()
    oTxtNew.Left = 15
    oTxtNew.Top = iControlTop + 22
    oTxtNew.Width = 200
    ' Pre-fill priority:
    '  1) oResult.sReplace already set (Mode 6 Copy Design - new prefix confirmed in prior form)
    '  2) Fall back to parsing the P-prefix from the active drawing filename
    If Trim(oResult.sReplace) <> "" Then
        oTxtNew.Text = Trim(oResult.sReplace)
    Else
        Try
            Dim sDwgName As String = System.IO.Path.GetFileNameWithoutExtension(ThisApplication.ActiveDocument.FullFileName)
            Dim iDash As Integer = sDwgName.IndexOf("-")
            If iDash > 0 Then
                oTxtNew.Text = sDwgName.Substring(0, iDash)
            End If
        Catch
        End Try
    End If
    oForm.Controls.Add(oTxtNew)

    Dim oLblNote As New Label()
    oLblNote.Text = "e.g. PJ00888  — the full new prefix, without the separator"
    oLblNote.Left = 225
    oLblNote.Top = iControlTop + 25
    oLblNote.Width = 290
    oForm.Controls.Add(oLblNote)

    Dim iBtnTop As Integer = iControlTop + 60
    Dim oBtnOk As New Button()
    oBtnOk.Text = "Run Batch Swap"
    oBtnOk.DialogResult = DialogResult.OK
    oBtnOk.Left = 290
    oBtnOk.Top = iBtnTop
    oBtnOk.Width = 110
    oForm.Controls.Add(oBtnOk)
    oForm.AcceptButton = oBtnOk

    Dim oBtnCancel As New Button()
    oBtnCancel.Text = "Cancel"
    oBtnCancel.DialogResult = DialogResult.Cancel
    oBtnCancel.Left = 415
    oBtnCancel.Top = iBtnTop
    oBtnCancel.Width = 90
    oForm.Controls.Add(oBtnCancel)
    oForm.CancelButton = oBtnCancel

    If oForm.ShowDialog() <> DialogResult.OK Then Return False

    ' Validate
    Dim sNewPrefix As String = Trim(oTxtNew.Text)
    If sNewPrefix = "" Then
        MessageBox.Show("New project number must be filled in - cancelled.", "Cancelled")
        Return False
    End If

    Dim oSelected As New System.Collections.Generic.List(Of String)
    For Each oChk As CheckBox In oCheckboxes
        If oChk.Checked Then oSelected.Add(Trim(CStr(oChk.Tag)))
    Next

    If oSelected.Count = 0 Then
        MessageBox.Show("No prefixes selected - cancelled.", "Cancelled")
        Return False
    End If

    oResult.oBatchFinds = oSelected
    oResult.sReplace = sNewPrefix
    Return True

End Function



' ---------------------------------------------------------------------
' BOLTED CONNECTION ASSEMBLY DETECTION
' Detects assemblies created by Inventor's Design Accelerator Bolted
' Connection Generator. These assemblies have DA-managed fastener
' occurrences that cannot be replaced via the normal ComponentOccurrence
' API (Replace() is blocked). File-level ReferencedFileDescriptors must
' be used instead.
'
' Detection: tries the formal DesignAcceleratorManager API first (most
' reliable). Falls back to heuristics: occurrence names matching DA
' naming patterns (no project prefix, just standard names like
' "AS 1252 M 20:1") and the parent occurrence name containing "Bolted".
' ---------------------------------------------------------------------
Function IsBoltedConnectionAssembly(oCompDef As ComponentDefinition) As Boolean
    ' Method 1: DesignAcceleratorManager API (Inventor 2014+)
    Try
        Dim oDAM As Object = oCompDef.DesignAcceleratorManager
        If oDAM IsNot Nothing Then
            Dim oFeatures As Object = oDAM.DesignAcceleratorFeatures
            If oFeatures IsNot Nothing AndAlso oFeatures.Count > 0 Then
                Return True
            End If
        End If
    Catch
    End Try

    ' Method 2: Name-based - BC assemblies follow Inventor's Bolted Connection
    ' naming convention: assembly name ends with "-BC" + digits.
    ' e.g. PJ00999-3280-01-V01-03-BC035.iam, PJ00174-3280-01-V01-03-BC000.iam
    Try
        Dim sAsmName As String = ""
        Try : sAsmName = System.IO.Path.GetFileNameWithoutExtension(oCompDef.Document.FullFileName).ToUpper() : Catch : End Try
        If sAsmName <> "" AndAlso System.Text.RegularExpressions.Regex.IsMatch(sAsmName, "-BC\d+$") Then Return True
    Catch
    End Try

    ' Method 3: Content heuristic - BC assemblies contain ONLY standard fasteners.
    ' Standard fastener designations appear ANYWHERE in the name, even when
    ' project-prefixed (e.g. PJ174-AS 1252 - M 20 contains 'AS 1252').
    Dim iStdFasteners As Integer = 0
    Dim iTotal As Integer = 0
    Try
        For Each oOcc As ComponentOccurrence In oCompDef.Occurrences
            iTotal = iTotal + 1
            Try
                Dim sN As String = System.IO.Path.GetFileNameWithoutExtension(oOcc.Definition.Document.FullFileName).ToUpper()
                ' Check for standard fastener designation ANYWHERE in name
                If sN.Contains("AS 1252") OrElse sN.Contains("AS 1110") OrElse _
                   sN.Contains("AS 1112") OrElse sN.Contains("AS 1237") OrElse _
                   sN.Contains("DIN ") OrElse sN.Contains("ISO ") OrElse _
                   sN.Contains("ANSI ") OrElse _
                   System.Text.RegularExpressions.Regex.IsMatch(sN, "AS\s*\d{3,4}") Then
                    iStdFasteners = iStdFasteners + 1
                End If
            Catch
            End Try
        Next
    Catch
    End Try
    ' All (or nearly all) occurrences are standard fasteners = DA Bolted Connection
    If iTotal > 0 AndAlso iStdFasteners >= 1 AndAlso _
       CDbl(iStdFasteners) / CDbl(iTotal) >= 0.5 Then Return True

    Return False
End Function


' ---------------------------------------------------------------------
' BOLTED CONNECTION REFERENCE REPOINTING
' For DA-protected assemblies where oRepOcc.Replace() is blocked,
' uses File.ReferencedFileDescriptors to repoint fastener file references
' directly in the assembly file header. This bypasses DA occurrence
' protection entirely and works reliably for all Inventor versions.
'
' Returns True if any references were updated.
' ---------------------------------------------------------------------
Function ProcessBoltedConnectionRefs(oAsmDoc As Document, sFind As String, sReplace As String, _
    bUseContainsMode As Boolean, sTargetFolder As String, _
    oLog As System.Text.StringBuilder, ByRef iCount As Integer, _
    ByRef oRenameMap As System.Collections.Generic.Dictionary(Of String, String)) As Boolean

    Dim bChanged As Boolean = False
    Dim sDocName As String = System.IO.Path.GetFileName(oAsmDoc.FullFileName)

    For Each oFD As FileDescriptor In oAsmDoc.File.ReferencedFileDescriptors
        Dim sRefFull As String = ""
        Try : sRefFull = oFD.FullFileName : Catch : Continue For : End Try
        If Trim(sRefFull) = "" Then Continue For
        If IsInExcludedFolder(sRefFull) Then Continue For

        Dim sRefName As String = System.IO.Path.GetFileNameWithoutExtension(sRefFull)
        Dim sRefExt  As String = System.IO.Path.GetExtension(sRefFull)

        ' Already renamed this run?
        If oRenameMap.ContainsKey(sRefFull) Then
            Dim sKnown As String = oRenameMap(sRefFull)
            If String.Compare(sKnown, sRefFull, True) <> 0 Then
                Try
                    oFD.ReplaceReference(sKnown)
                    bChanged = True
                    oLog.Append(vbCrLf & "  BOLTED-CONN FD REPOINT (via rename map): " & sRefName & sRefExt & "  -->  " & System.IO.Path.GetFileName(sKnown) & "  [" & sDocName & "]")
                Catch exKnown As Exception
                    oLog.Append(vbCrLf & "  BOLTED-CONN FD REPOINT FAILED: " & sRefName & sRefExt & " (" & exKnown.Message & ")")
                End Try
            End If
            Continue For
        End If

        ' Does this reference match our Find pattern?
        Dim bMatch As Boolean
        If bUseContainsMode Then
            bMatch = sRefName.ToUpper().Contains(sFind.ToUpper())
        Else
            bMatch = sRefName.ToUpper().StartsWith(sFind.ToUpper())
        End If
        If Not bMatch Then Continue For

        ' Compute new name
        Dim sNewName As String
        If bUseContainsMode Then
            sNewName = ReplaceAllCaseInsensitive(sRefName, sFind, sReplace)
        Else
            sNewName = sReplace & sRefName.Substring(sFind.Length)
        End If
        Dim sNewFull As String = System.IO.Path.Combine(sTargetFolder, sNewName & sRefExt)

        ' Target must exist (created by the main batch pass or previous run).
        ' If not, copy it now from the source - fasteners are DA-managed library
        ' parts that are excluded from the main traversal but still need a
        ' renamed copy in the target folder so the BC assembly can reference it.
        If Not System.IO.File.Exists(sNewFull) Then
            If System.IO.File.Exists(sRefFull) Then
                Try
                    System.IO.File.Copy(sRefFull, sNewFull, True)
                    ' Clear read-only: Vault-checked-in sources are RO on disk;
                    ' the copy inherits that attribute and triggers Vault's
                    ' "not vaulted and read-only - allow editing?" popup.
                    Try
                        Dim oAttrs As System.IO.FileAttributes = System.IO.File.GetAttributes(sNewFull)
                        If (oAttrs And System.IO.FileAttributes.ReadOnly) = System.IO.FileAttributes.ReadOnly Then
                            System.IO.File.SetAttributes(sNewFull, oAttrs And Not System.IO.FileAttributes.ReadOnly)
                        End If
                    Catch
                    End Try
                    oLog.Append(vbCrLf & "  BOLTED-CONN FD: copied fastener to target: " & sNewName & sRefExt)
                Catch exCopy As Exception
                    oLog.Append(vbCrLf & "  BOLTED-CONN FD: target not yet on disk and copy failed - " & sNewName & sRefExt & " (" & exCopy.Message & ")")
                    Continue For
                End Try
            Else
                oLog.Append(vbCrLf & "  BOLTED-CONN FD: target not yet on disk and source missing - " & sNewName & sRefExt & " (run full batch pass first)")
                Continue For
            End If
        End If

        Try
            oFD.ReplaceReference(sNewFull)
            oRenameMap(sRefFull) = sNewFull
            iCount = iCount + 1
            bChanged = True
            oLog.Append(vbCrLf & "  BOLTED-CONN FD REPOINT: " & sRefName & sRefExt & "  -->  " & sNewName & sRefExt & "  [" & sDocName & "]")
        Catch exFD As Exception
            oLog.Append(vbCrLf & "  BOLTED-CONN FD REPOINT FAILED: " & sRefName & sRefExt & " (" & exFD.Message & ")")
        End Try
    Next

    Return bChanged
End Function


' ---------------------------------------------------------------------
' FRAME GENERATOR - broad detection + package processing (Mode 1)
' Detects: assembly name contains FRAME or ends with -F;
'          child SKEL/SKELETON; children in \Frame\ folder;
'          SF- members; multiple AS+digit structural members.
' ---------------------------------------------------------------------
Function IsFrameGeneratorAssembly(oCompDef As ComponentDefinition, Optional sAsmFullPath As String = "") As Boolean
    ' 1) Assembly file name itself
    Try
        Dim sAsmName As String = ""
        If sAsmFullPath <> "" Then
            sAsmName = System.IO.Path.GetFileNameWithoutExtension(sAsmFullPath).ToUpper()
        Else
            Try : sAsmName = System.IO.Path.GetFileNameWithoutExtension(oCompDef.Document.FullFileName).ToUpper() : Catch : End Try
        End If
        If sAsmName.Contains("FRAME") Then Return True
        If sAsmName.EndsWith("-F") OrElse sAsmName.EndsWith("_F") Then Return True
        ' Handle suffix after -F or _F (e.g. -F_ReferenceCopy, -F_MiR)
        If System.Text.RegularExpressions.Regex.IsMatch(sAsmName, "-F[_\s]|_F[_\s]", System.Text.RegularExpressions.RegexOptions.IgnoreCase) Then Return True
    Catch
    End Try

    Dim iSkel As Integer = 0
    Dim iMem As Integer = 0
    Dim iAsMem As Integer = 0
    Dim iInFrameFolder As Integer = 0
    Try
        For Each oOcc As ComponentOccurrence In oCompDef.Occurrences
            Dim sN As String = ""
            Dim sFull As String = ""
            Try
                sFull = oOcc.Definition.Document.FullFileName
                sN = System.IO.Path.GetFileName(sFull).ToUpper()
            Catch
                Try : sN = oOcc.Name.ToUpper() : Catch : End Try
            End Try
            If sN = "" Then Continue For

            If sN.Contains("SKELETON") OrElse sN.Contains("-SKEL") OrElse sN.Contains("_SKEL") OrElse sN.Contains(" SKEL") OrElse sN.EndsWith("SKEL.IPT") Then
                iSkel = iSkel + 1
            End If
            If sN.Contains("-SF-") OrElse sN.Contains("_SF_") OrElse System.Text.RegularExpressions.Regex.IsMatch(sN, "-SF\d") Then
                iMem = iMem + 1
            End If
            ' FG structural shapes: "AS 3679 ..." or "AS 1252 ..." with long digit runs
            If System.Text.RegularExpressions.Regex.IsMatch(sN, "^AS\s*\d+") AndAlso System.Text.RegularExpressions.Regex.IsMatch(sN, "\d{8,}") Then
                iAsMem = iAsMem + 1
            End If
            If sFull <> "" Then
                Dim sFolder As String = System.IO.Path.GetDirectoryName(sFull).ToUpper()
                If sFolder.EndsWith("\FRAME") OrElse sFolder.Contains("\FRAME\") Then
                    iInFrameFolder = iInFrameFolder + 1
                End If
            End If
        Next
    Catch
        Return False
    End Try

    If iSkel >= 1 Then Return True
    If iMem >= 2 Then Return True
    If iAsMem >= 3 Then Return True
    If iInFrameFolder >= 3 Then Return True
    Return False
End Function


Function GetFrameTargetFolder(sOldFullName As String, sMainTargetFolder As String) As String
    Dim sFileFolder As String = System.IO.Path.GetDirectoryName(sOldFullName)
    Try
        Dim sOriginalRoot As String = System.IO.Path.GetDirectoryName(sMainTargetFolder.TrimEnd(System.IO.Path.DirectorySeparatorChar))
        If sOriginalRoot <> "" Then
            Dim sFileFolderU As String = sFileFolder.TrimEnd(System.IO.Path.DirectorySeparatorChar).ToUpper()
            Dim sOriginalRootU As String = sOriginalRoot.TrimEnd(System.IO.Path.DirectorySeparatorChar).ToUpper()
            If sFileFolderU.StartsWith(sOriginalRootU & System.IO.Path.DirectorySeparatorChar) Then
                Dim sRelative As String = sFileFolder.Substring(sOriginalRoot.Length + 1).TrimEnd(System.IO.Path.DirectorySeparatorChar)
                Dim sTargetFolderName As String = System.IO.Path.GetFileName(sMainTargetFolder.TrimEnd(System.IO.Path.DirectorySeparatorChar))
                If sRelative <> "" AndAlso Not sRelative.ToUpper().StartsWith(sTargetFolderName.ToUpper()) Then
                    Dim sMirroredFolder As String = System.IO.Path.Combine(sMainTargetFolder, sRelative)
                    Try
                        If Not System.IO.Directory.Exists(sMirroredFolder) Then System.IO.Directory.CreateDirectory(sMirroredFolder)
                        Return sMirroredFolder
                    Catch
                    End Try
                End If
            End If
        End If
    Catch
    End Try
    Dim sParentName As String = System.IO.Path.GetFileName(sFileFolder)
    If String.Compare(sParentName, "Frame", True) = 0 Then
        Dim sFrameFolder As String = System.IO.Path.Combine(sMainTargetFolder, "Frame")
        Try
            If Not System.IO.Directory.Exists(sFrameFolder) Then System.IO.Directory.CreateDirectory(sFrameFolder)
            Return sFrameFolder
        Catch
        End Try
    End If
    Return sMainTargetFolder
End Function


Function ComputeRenamedFileName(sOldNameNoExt As String, sFind As String, sReplace As String, bUseContainsMode As Boolean) As String
    If bUseContainsMode Then
        Return ReplaceAllCaseInsensitive(sOldNameNoExt, sFind, sReplace)
    Else
        If sOldNameNoExt.ToUpper().StartsWith(sFind.ToUpper()) Then
            Return sReplace & sOldNameNoExt.Substring(sFind.Length)
        Else
            Return ReplaceAllCaseInsensitive(sOldNameNoExt, sFind, sReplace)
        End If
    End If
End Function


Function ProcessFrameGeneratorSet( _
    oFrameDoc As Document, _
    oRepOcc As ComponentOccurrence, _
    sFind As String, _
    sReplace As String, _
    bUseContainsMode As Boolean, _
    sTargetFolder As String, _
    sTopAssemblyFullName As String, _
    oLog As System.Text.StringBuilder, _
    ByRef iCount As Integer, _
    ByRef oRenameMap As System.Collections.Generic.Dictionary(Of String, String), _
    sLogFilePath As String, _
    Optional oBatchAllFinds As System.Collections.Generic.List(Of String) = Nothing, _
    Optional sAllReplace As String = "") As Boolean

    Dim sFrameOldFull As String = oFrameDoc.FullFileName
    Dim sFrameOldName As String = System.IO.Path.GetFileNameWithoutExtension(sFrameOldFull)
    Dim sFrameExt As String = System.IO.Path.GetExtension(sFrameOldFull)

    oLog.Append(vbCrLf & "FRAME GENERATOR SET detected: " & sFrameOldName & sFrameExt)

    Dim oSetOldPaths As New System.Collections.Generic.List(Of String)
    oSetOldPaths.Add(sFrameOldFull)

    Try
        For Each oOcc As ComponentOccurrence In oFrameDoc.ComponentDefinition.Occurrences
            Dim sChildFull As String = ""
            Try
                sChildFull = oOcc.Definition.Document.FullFileName
            Catch
                Try : sChildFull = oOcc.ReferencedFileDescriptor.FullFileName : Catch : End Try
            End Try
            If sChildFull = "" OrElse sChildFull.Contains("*") Then Continue For
            If Not oSetOldPaths.Contains(sChildFull) Then oSetOldPaths.Add(sChildFull)
        Next
    Catch ex As Exception
        oLog.Append(vbCrLf & "  FRAME: failed enumerating children: " & ex.Message)
    End Try

    oLog.Append(vbCrLf & "  FRAME: package contains " & oSetOldPaths.Count & " file(s) (asm + children)")

    Dim oLocalMap As New System.Collections.Generic.Dictionary(Of String, String)

    For Each sOldFull As String In oSetOldPaths
        If oRenameMap.ContainsKey(sOldFull) Then
            oLocalMap(sOldFull) = oRenameMap(sOldFull)
            Continue For
        End If

        Dim sOldName As String = System.IO.Path.GetFileNameWithoutExtension(sOldFull)
        Dim sExt As String = System.IO.Path.GetExtension(sOldFull)
        ' FIX C: try primary sFind first, then each batch token in turn.
        ' Frame members may have a DIFFERENT prefix than the current pass
        ' (e.g. PJ00174 members inside a PJ00145 frame assembly). Without
        ' this, ComputeRenamedFileName returns the name unchanged and
        ' PJ00174-named files are copied to target with their old name.
        Dim sNewName As String = ComputeRenamedFileName(sOldName, sFind, sReplace, bUseContainsMode)
        ' If primary sFind didn't match, try other batch tokens
        If String.Compare(sNewName, sOldName, True) = 0 AndAlso _
           oBatchAllFinds IsNot Nothing AndAlso sAllReplace <> "" Then
            For Each sOtherFind As String In oBatchAllFinds
                If String.Compare(sOtherFind, sFind, True) <> 0 Then
                    Dim sTryName As String = ComputeRenamedFileName(sOldName, sOtherFind, sAllReplace, False)
                    If String.Compare(sTryName, sOldName, True) <> 0 Then
                        sNewName = sTryName
                        Exit For
                    End If
                End If
            Next
        End If
        Dim sDestFolder As String = GetFrameTargetFolder(sOldFull, sTargetFolder)
        Dim sNewFull As String = System.IO.Path.Combine(sDestFolder, sNewName & sExt)

        If String.Compare(sNewFull, sTopAssemblyFullName, True) = 0 Then
            oLocalMap(sOldFull) = sOldFull
            Continue For
        End If

        If System.IO.File.Exists(sNewFull) Then
            oLocalMap(sOldFull) = sNewFull
            oRenameMap(sOldFull) = sNewFull
            oLog.Append(vbCrLf & "  FRAME (already existed): " & sOldName & sExt & "  -->  " & sNewName & sExt)
            Continue For
        End If

        Dim bOk As Boolean = False
        Try
            If Not System.IO.Directory.Exists(sDestFolder) Then System.IO.Directory.CreateDirectory(sDestFolder)
            System.IO.File.Copy(sOldFull, sNewFull, False)
            Try
                Dim oAttrs As System.IO.FileAttributes = System.IO.File.GetAttributes(sNewFull)
                If (oAttrs And System.IO.FileAttributes.ReadOnly) = System.IO.FileAttributes.ReadOnly Then
                    System.IO.File.SetAttributes(sNewFull, oAttrs And Not System.IO.FileAttributes.ReadOnly)
                End If
            Catch
            End Try
            bOk = System.IO.File.Exists(sNewFull)
        Catch exCopy As Exception
            oLog.Append(vbCrLf & "  FRAME copy FAILED: " & sOldName & sExt & " (" & exCopy.Message & ")")
        End Try

        If bOk Then
            oLocalMap(sOldFull) = sNewFull
            oRenameMap(sOldFull) = sNewFull
            iCount = iCount + 1
            oLog.Append(vbCrLf & "  FRAME copied: " & sOldName & sExt & "  -->  " & sNewName & sExt & "  [" & sDestFolder & "]")
        Else
            oLocalMap(sOldFull) = sOldFull
        End If
    Next

    Dim sFrameNewFull As String = oLocalMap(sFrameOldFull)
    If String.Compare(sFrameNewFull, sFrameOldFull, True) = 0 Then
        oLog.Append(vbCrLf & "  FRAME: frame assembly was not copied - aborting set repoint")
        Return False
    End If

    Dim bFrameOpenedHere As Boolean = False
    Dim oNewFrameDoc As Document = OpenDocTracked(sFrameNewFull, bFrameOpenedHere)
    If oNewFrameDoc Is Nothing Then
        oLog.Append(vbCrLf & "  FRAME: failed to open new frame assembly")
        Return False
    End If

    Try
        Dim oFa As System.IO.FileAttributes = System.IO.File.GetAttributes(sFrameNewFull)
        If (oFa And System.IO.FileAttributes.ReadOnly) = System.IO.FileAttributes.ReadOnly Then
            System.IO.File.SetAttributes(sFrameNewFull, oFa And Not System.IO.FileAttributes.ReadOnly)
        End If
    Catch
    End Try

    Dim iRepointed As Integer = 0
    Try
        Dim oNewOccList As New System.Collections.Generic.List(Of ComponentOccurrence)
        For Each oOcc As ComponentOccurrence In oNewFrameDoc.ComponentDefinition.Occurrences
            oNewOccList.Add(oOcc)
        Next
        For Each oOcc As ComponentOccurrence In oNewOccList
            Dim sOccFull As String = ""
            Try
                sOccFull = oOcc.Definition.Document.FullFileName
            Catch
                Try : sOccFull = oOcc.ReferencedFileDescriptor.FullFileName : Catch : End Try
            End Try
            If sOccFull = "" Then Continue For
            If oLocalMap.ContainsKey(sOccFull) AndAlso String.Compare(oLocalMap(sOccFull), sOccFull, True) <> 0 Then
                Try
                    oOcc.Replace(oLocalMap(sOccFull), False)
                    Try : oOcc.Name = System.IO.Path.GetFileNameWithoutExtension(oLocalMap(sOccFull)) : Catch : End Try
                    iRepointed = iRepointed + 1
                Catch exRep As Exception
                    oLog.Append(vbCrLf & "  FRAME: failed to repoint child '" & oOcc.Name & "': " & exRep.Message)
                End Try
            End If
        Next
    Catch ex As Exception
        oLog.Append(vbCrLf & "  FRAME: error during child repoint: " & ex.Message)
    End Try

    oLog.Append(vbCrLf & "  FRAME: repointed " & iRepointed & " child occurrence(s) inside new frame assembly")

    Try
        oNewFrameDoc.Update()
        oNewFrameDoc.Save2(False)
        oLog.Append(vbCrLf & "  FRAME: saved new frame assembly")
    Catch exSave As Exception
        oLog.Append(vbCrLf & "  FRAME: initial save failed (" & exSave.Message & ") - trying save-together")
        ' Docs opened here for save-together; closed after the retry save below
        Dim oRelOpenedHere As New System.Collections.Generic.List(Of Document)
        For Each kvp As System.Collections.Generic.KeyValuePair(Of String, String) In oLocalMap
            If String.Compare(kvp.Key, kvp.Value, True) = 0 Then Continue For
            If String.Compare(kvp.Value, sFrameNewFull, True) = 0 Then Continue For
            Try
                Dim oRelDoc As Document = Nothing
                Try : oRelDoc = ThisApplication.Documents.ItemByName(kvp.Value) : Catch : oRelDoc = Nothing : End Try
                If oRelDoc Is Nothing AndAlso System.IO.File.Exists(kvp.Value) Then
                    Dim bRelOpenedHere As Boolean = False
                    oRelDoc = OpenDocTracked(kvp.Value, bRelOpenedHere)
                    If bRelOpenedHere AndAlso oRelDoc IsNot Nothing Then oRelOpenedHere.Add(oRelDoc)
                End If
                If oRelDoc IsNot Nothing Then
                    Try
                        Dim oRa As System.IO.FileAttributes = System.IO.File.GetAttributes(kvp.Value)
                        If (oRa And System.IO.FileAttributes.ReadOnly) = System.IO.FileAttributes.ReadOnly Then
                            System.IO.File.SetAttributes(kvp.Value, oRa And Not System.IO.FileAttributes.ReadOnly)
                        End If
                    Catch
                    End Try
                    Try : oRelDoc.Save2(False) : Catch : End Try
                End If
            Catch
            End Try
        Next
        Try
            oNewFrameDoc.Save2(False)
            oLog.Append(vbCrLf & "  FRAME: save-together succeeded")
        Catch exSave2 As Exception
            oLog.Append(vbCrLf & "  FRAME: save-together still failed: " & exSave2.Message)
        End Try
        For Each oRelClose As Document In oRelOpenedHere
            CloseIfOpenedHere(oRelClose, True)
        Next
    End Try

    Dim bParentOk As Boolean = False
    Try
        Try
            Dim sParentPath As String = oRepOcc.Parent.Document.FullFileName
            Dim oPa As System.IO.FileAttributes = System.IO.File.GetAttributes(sParentPath)
            If (oPa And System.IO.FileAttributes.ReadOnly) = System.IO.FileAttributes.ReadOnly Then
                System.IO.File.SetAttributes(sParentPath, oPa And Not System.IO.FileAttributes.ReadOnly)
            End If
        Catch
        End Try
        oRepOcc.Replace(sFrameNewFull, False)
        Try : oRepOcc.Name = System.IO.Path.GetFileNameWithoutExtension(sFrameNewFull) : Catch : End Try
        bParentOk = True
        iCount = iCount + 1
        oLog.Append(vbCrLf & "  FRAME: parent occurrence repointed to " & System.IO.Path.GetFileName(sFrameNewFull))
    Catch exPar As Exception
        oLog.Append(vbCrLf & "  FRAME: failed to repoint parent occurrence: " & exPar.Message)
    End Try

        CloseIfOpenedHere(oNewFrameDoc, bFrameOpenedHere)
    oNewFrameDoc = Nothing

    Return bParentOk

End Function
