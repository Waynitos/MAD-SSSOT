' iLogic ASSASSIN — Interactive Active Sheet Override Review
' Inventor 2025 | PROPOSED for runtime testing
' WARNING: Restore actions change drawing dimensions. No automatic save.
Sub Main()

    Dim doc As Inventor.DrawingDocument = TryCast( _
        ThisApplication.ActiveDocument, Inventor.DrawingDocument)
    If doc Is Nothing Then
        MessageBox.Show("Open an Inventor drawing first.", "ASSASSIN")
        Exit Sub
    End If

    Dim sheet As Inventor.Sheet = doc.ActiveSheet
    Dim matches As New System.Collections.Generic.List(Of Inventor.GeneralDimension)
    Dim dimItem As Inventor.GeneralDimension = Nothing
    Dim scanErrors As Integer = 0

    Try
        For Each dimItem In sheet.DrawingDimensions.GeneralDimensions
            Try
                If dimItem.ModelValueOverridden Then
                    matches.Add(dimItem)
                End If
            Catch ex As Exception
                scanErrors += 1
            End Try
        Next
    Catch ex As Exception
        MessageBox.Show("Scan failed: " & ex.Message, "ASSASSIN")
        Exit Sub
    End Try

    If matches.Count = 0 Then
        MessageBox.Show("No numeric overrides found on " & sheet.Name & _
            "." & vbCrLf & "Inspection errors: " & scanErrors.ToString(), "ASSASSIN")
        Exit Sub
    End If

    Dim choice As Integer = ChooseAction( _
        "Found " & matches.Count.ToString() & " numeric overrides on " & sheet.Name & _
        ". Inspection errors: " & scanErrors.ToString(), _
        "Inspect each dimension (zoom and review)", _
        "Restore all overrides (confirmation required)", _
        "Leave unchanged")

    If choice = 0 Or choice = 3 Then Exit Sub

    Dim restored As Integer = 0
    Dim leftAlone As Integer = 0
    Dim failed As Integer = 0
    Dim index As Integer = 0

    If choice = 2 Then
        Dim confirm As System.Windows.Forms.DialogResult = _
            System.Windows.Forms.MessageBox.Show( _
            "Restore all " & matches.Count.ToString() & _
            " numeric overrides on " & sheet.Name & "?" & vbCrLf & _
            "This changes the drawing in memory. It will NOT be saved automatically." & _
            vbCrLf & "Use a disposable copy or authorised editable drawing.", _
            "CONFIRM BULK RESTORATION", _
            System.Windows.Forms.MessageBoxButtons.YesNo, _
            System.Windows.Forms.MessageBoxIcon.Warning, _
            System.Windows.Forms.MessageBoxDefaultButton.Button2)

        If confirm <> System.Windows.Forms.DialogResult.Yes Then Exit Sub

        For Each dimItem In matches
            Try
                If dimItem.ModelValueOverridden Then
                    dimItem.ModelValueOverridden = False
                End If
                If dimItem.ModelValueOverridden Then
                    failed += 1
                Else
                    restored += 1
                End If
            Catch ex As Exception
                failed += 1
            End Try
        Next
    Else
        For Each dimItem In matches
            index += 1
            Try
                If Not dimItem.ModelValueOverridden Then
                    leftAlone += 1
                    Continue For
                End If

                Dim zoomNote As String = ZoomToDimension(doc, dimItem)
                Dim actualText As String = FormatDimensionValue(dimItem, False)
                Dim overrideText As String = FormatDimensionValue(dimItem, True)
                Dim shown As String = dimItem.Text.Text

                Dim prompt As String = "Override " & index.ToString() & _
                    " of " & matches.Count.ToString() & vbCrLf & _
                    "Sheet: " & sheet.Name & vbCrLf & _
                    "Actual: " & actualText & vbCrLf & _
                    "Override: " & overrideText & vbCrLf & _
                    "Displayed: " & shown & vbCrLf & _
                    "Location: " & zoomNote & vbCrLf & _
                    "Drawing will not be saved automatically."

                Dim answer As Integer = ChooseAction(prompt, _
                    "Leave as is; next dimension", _
                    "Restore actual model value", _
                    "Stop reviewing")

                If answer = 0 Or answer = 3 Then Exit For

                If answer = 2 Then
                    dimItem.ModelValueOverridden = False
                    If dimItem.ModelValueOverridden Then
                        failed += 1
                    Else
                        restored += 1
                    End If
                Else
                    leftAlone += 1
                End If
            Catch ex As Exception
                failed += 1
                MessageBox.Show("Dimension " & index.ToString() & _
                    " could not be reviewed/restored: " & ex.Message, "ASSASSIN")
            End Try
        Next
    End If

    MessageBox.Show("ACTIVE SHEET REVIEW COMPLETE" & vbCrLf & _
        "Sheet: " & sheet.Name & vbCrLf & _
        "Found: " & matches.Count.ToString() & vbCrLf & _
        "Restored: " & restored.ToString() & vbCrLf & _
        "Left unchanged/skipped: " & leftAlone.ToString() & vbCrLf & _
        "Errors: " & failed.ToString() & vbCrLf & _
        "Scan errors: " & scanErrors.ToString() & vbCrLf & vbCrLf & _
        "Drawing NOT saved automatically.", "ASSASSIN")

End Sub

Function FormatDimensionValue(ByVal dimItem As Inventor.GeneralDimension, _
                              ByVal useOverride As Boolean) As String
    Dim value As Double = dimItem.ModelValue
    If useOverride Then value = dimItem.OverrideModelValue

    If TypeOf dimItem Is Inventor.AngularGeneralDimension Then
        Return (value * 180.0 / System.Math.PI).ToString("0.#", _
            System.Globalization.CultureInfo.InvariantCulture) & " deg"
    End If

    Return (value * 10.0).ToString("0.#", _
        System.Globalization.CultureInfo.InvariantCulture) & " mm"
End Function

Function ZoomToDimension(ByVal doc As Inventor.DrawingDocument, _
                         ByVal dimItem As Inventor.GeneralDimension) As String
    Try
        Dim origin As Inventor.Point2d = dimItem.Text.Origin
        Dim camera As Inventor.Camera = ThisApplication.ActiveView.Camera
        Dim geometry As Inventor.TransientGeometry = ThisApplication.TransientGeometry

        camera.Target = geometry.CreatePoint(origin.X, origin.Y, 0)
        camera.Eye = geometry.CreatePoint(origin.X, origin.Y, 1)
        camera.SetExtents(12, 8)
        camera.ApplyWithoutTransition()

        Try
            doc.SelectSet.Clear()
            doc.SelectSet.Select(dimItem)
        Catch ex As Exception
            Return "Zoomed; selection unavailable: " & ex.Message
        End Try

        Return "Zoomed and selected"
    Catch ex As Exception
        Return "Zoom unavailable: " & ex.Message
    End Try
End Function

Function ChooseAction(ByVal heading As String, _
                      ByVal optionOne As String, _
                      ByVal optionTwo As String, _
                      ByVal optionThree As String) As Integer

    ' Size each dialog according to its heading text.
    ' Avoid System.Drawing Font/Size APIs blocked by the iLogic host.
    Dim lineCount As Integer = heading.Split( _
        New String() {vbCrLf}, System.StringSplitOptions.None).Length
    Dim headingHeight As Integer = System.Math.Max(26, lineCount * 17 + 8)
    Dim firstOptionTop As Integer = 16 + headingHeight + 8
    Dim buttonTop As Integer = firstOptionTop + 102

    Dim frm As New System.Windows.Forms.Form()
    frm.Text = "iLogic ASSASSIN - Choose Action"
    frm.Width = 390
    frm.Height = buttonTop + 86
    frm.StartPosition = System.Windows.Forms.FormStartPosition.CenterScreen
    frm.FormBorderStyle = System.Windows.Forms.FormBorderStyle.FixedDialog
    frm.MaximizeBox = False
    frm.MinimizeBox = False

    Dim lbl As New System.Windows.Forms.Label()
    lbl.Left = 18
    lbl.Top = 16
    lbl.Width = 345
    lbl.Height = headingHeight
    lbl.Text = heading

    Dim rb1 As New System.Windows.Forms.RadioButton()
    rb1.Left = 20
    rb1.Top = firstOptionTop
    rb1.Width = 345
    rb1.Text = optionOne
    rb1.Checked = True

    Dim rb2 As New System.Windows.Forms.RadioButton()
    rb2.Left = 20
    rb2.Top = firstOptionTop + 30
    rb2.Width = 345
    rb2.Text = optionTwo

    Dim rb3 As New System.Windows.Forms.RadioButton()
    rb3.Left = 20
    rb3.Top = firstOptionTop + 60
    rb3.Width = 345
    rb3.Text = optionThree

    Dim btnContinue As New System.Windows.Forms.Button()
    btnContinue.Text = "Continue"
    btnContinue.Left = 98
    btnContinue.Top = buttonTop
    btnContinue.Width = 90
    btnContinue.DialogResult = System.Windows.Forms.DialogResult.OK

    Dim btnCancel As New System.Windows.Forms.Button()
    btnCancel.Text = "Cancel"
    btnCancel.Left = 198
    btnCancel.Top = buttonTop
    btnCancel.Width = 90
    btnCancel.DialogResult = System.Windows.Forms.DialogResult.Cancel

    frm.Controls.Add(lbl)
    frm.Controls.Add(rb1)
    frm.Controls.Add(rb2)
    frm.Controls.Add(rb3)
    frm.Controls.Add(btnContinue)
    frm.Controls.Add(btnCancel)
    frm.AcceptButton = btnContinue
    frm.CancelButton = btnCancel

    Dim result As System.Windows.Forms.DialogResult = frm.ShowDialog()
    Dim selection As Integer = 0

    If result = System.Windows.Forms.DialogResult.OK Then
        If rb1.Checked Then selection = 1
        If rb2.Checked Then selection = 2
        If rb3.Checked Then selection = 3
    End If

    frm.Dispose()
    Return selection

End Function
