' =====================================================================
' iLogic Rule: Repoint JC00 / Content Center Duplicates To Library Original
' (run from inside an ASSEMBLY)
'
' Version: 2026-10-27c
'   - JC Catalogue and CC Catalogue modes now AUTO-BUILD the catalogue
'     on first run if the text file does not exist - no separate builder
'     rule needed.  Catalogue lives in the library root folder so it can
'     be checked in to Vault and shared across the team.
'   - CC Catalogue (FAST) mode added: same geometry-match logic as JC,
'     scanning C:\Vault\Content Center Files for .ipt (and .iam) parts.
'   - Picker only shows parts with a confirmed identical match.
'   - Select All -> Library / Select All -> Keep buttons in picker.
'
' Catalogue file locations (check these in to Vault):
'   JC:  C:\Vault\Libraries\JC Library\JC_Library_Catalogue.txt
'   CC:  C:\Vault\Content Center Files\CC_Catalogue.txt
'
' PHASE 3 OF 3 - THIS RULE CHANGES FILES.
'   Phase 1: Test_Find_JC00_Library_Candidates.iLogicVb  (report only)
'   Phase 2: Test_Compare_JC00_Geometry.iLogicVb         (report only)
'   Phase 3: this rule - shows a picker, then repoints chosen occurrences.
'
' TOLERANCES: 0.1% relative on Mass/Volume/Area, 0.01mm absolute on CoM.
' =====================================================================

Sub Main()

    ' ---------- Config ----------
    Dim sLibraryFolder       As String = "C:\Vault\Libraries\JC Library"
    Dim sContentCenterFolder As String = "C:\Vault\Content Center Files"
    Dim sTokenPattern        As String = "JC00\d+"
    Dim sJCCatalogueFile     As String = System.IO.Path.Combine(sLibraryFolder, "JC_Library_Catalogue.txt")
    Dim sCCCatalogueFile     As String = System.IO.Path.Combine(sContentCenterFolder, "CC_Catalogue.txt")

    ' Fastener/hardware keywords for Content Center live-scan duplicate detection
    Dim oFastenerKeywords As String() = New String() { _
        "M6", "M8", "M10", "M12", "M16", "M20", "M24", "M27", "M30", _
        "DIN", "ISO", "ASTM", "AS ", "AS1", "AS4", _
        "FLANGE", "WASHER", "NUT", "BOLT", "SCREW", "STUD", _
        "GASKET", "NYLOCK", "DRIVE SCREW", "BLIND FLANGE"}

    ' ---------- Mode selection ----------
    Dim bModeJC          As Boolean = False
    Dim bModeCC          As Boolean = False
    Dim bModeInternal    As Boolean = False
    Dim bModeJCCatalogue As Boolean = False
    Dim bModeCCCatalogue As Boolean = False
    Dim bReportOnly As Boolean = False
    ShowModeSelectionForm(bModeJC, bModeCC, bModeInternal, bModeJCCatalogue, bModeCCCatalogue, bReportOnly)
    If Not bModeJC AndAlso Not bModeCC AndAlso Not bModeInternal AndAlso Not bModeJCCatalogue AndAlso Not bModeCCCatalogue Then Exit Sub

    ' ---------- Basic checks ----------
    Dim oAsmDoc As AssemblyDocument
    Try
        oAsmDoc = ThisApplication.ActiveDocument
    Catch
        MessageBox.Show("Could not get the active document.", "Error")
        Exit Sub
    End Try
    If oAsmDoc.DocumentType <> kAssemblyDocumentObject Then
        MessageBox.Show("This rule needs to be run from inside an assembly document.", "Wrong Document Type")
        Exit Sub
    End If

    Dim sTopAssemblyFullName As String = oAsmDoc.FullFileName

    ' ---------- JC Catalogue ----------
    Dim oJCEntries    As New List(Of CatalogueEntry)
    Dim oJCMassBucket As New Dictionary(Of String, List(Of CatalogueEntry))()
    If bModeJCCatalogue Then
        If Not System.IO.Directory.Exists(sLibraryFolder) Then
            MessageBox.Show("JC Library folder not found:" & vbCrLf & sLibraryFolder, "Folder Not Found")
            Exit Sub
        End If
        If Not System.IO.File.Exists(sJCCatalogueFile) Then
            Dim oBuild As DialogResult = MessageBox.Show( _
                "JC Library catalogue not found." & vbCrLf & sCatalogueFilePath(sJCCatalogueFile) & vbCrLf & vbCrLf & _
                "Build it now? Inventor will open every .ipt/.iam in the JC Library once to read geometry." & vbCrLf & _
                "This may take several minutes. The catalogue is saved for future runs.", _
                "Build JC Catalogue?", MessageBoxButtons.YesNo, MessageBoxIcon.Question)
            If oBuild <> DialogResult.Yes Then Exit Sub
            BuildCatalogue(sLibraryFolder, sJCCatalogueFile, True)
            If Not System.IO.File.Exists(sJCCatalogueFile) Then
                MessageBox.Show("Catalogue build failed - cannot continue.", "Error")
                Exit Sub
            End If
        End If
        LoadCatalogue(sJCCatalogueFile, oJCEntries, oJCMassBucket)
        If oJCEntries.Count = 0 Then
            MessageBox.Show("JC Catalogue is empty or unreadable:" & vbCrLf & sJCCatalogueFile, "Catalogue Empty")
            Exit Sub
        End If
    End If

    ' ---------- CC Catalogue ----------
    Dim oCCEntries    As New List(Of CatalogueEntry)
    Dim oCCMassBucket As New Dictionary(Of String, List(Of CatalogueEntry))()
    If bModeCCCatalogue Then
        If Not System.IO.Directory.Exists(sContentCenterFolder) Then
            MessageBox.Show("Content Center folder not found:" & vbCrLf & sContentCenterFolder, "Folder Not Found")
            Exit Sub
        End If
        If Not System.IO.File.Exists(sCCCatalogueFile) Then
            Dim oBuildCC As DialogResult = MessageBox.Show( _
                "Content Center catalogue not found." & vbCrLf & sCCCatalogueFile & vbCrLf & vbCrLf & _
                "Build it now? Inventor will open every .ipt in the Content Center folder once to read geometry." & vbCrLf & _
                "This may take several minutes. The catalogue is saved for future runs.", _
                "Build CC Catalogue?", MessageBoxButtons.YesNo, MessageBoxIcon.Question)
            If oBuildCC <> DialogResult.Yes Then Exit Sub
            BuildCatalogue(sContentCenterFolder, sCCCatalogueFile, False)
            If Not System.IO.File.Exists(sCCCatalogueFile) Then
                MessageBox.Show("CC Catalogue build failed - cannot continue.", "Error")
                Exit Sub
            End If
        End If
        LoadCatalogue(sCCCatalogueFile, oCCEntries, oCCMassBucket)
        If oCCEntries.Count = 0 Then
            MessageBox.Show("CC Catalogue is empty or unreadable:" & vbCrLf & sCCCatalogueFile, "Catalogue Empty")
            Exit Sub
        End If
    End If

    If bModeJC AndAlso Not System.IO.Directory.Exists(sLibraryFolder) Then
        MessageBox.Show("JC Library folder not found:" & vbCrLf & sLibraryFolder, "Folder Not Found")
        Exit Sub
    End If
    If bModeCC AndAlso Not System.IO.Directory.Exists(sContentCenterFolder) Then
        MessageBox.Show("Content Center Files folder not found:" & vbCrLf & sContentCenterFolder, "Folder Not Found")
        Exit Sub
    End If

    ' ---------- Disk log ----------
    Dim sLogFolder As String = "C:\Temp\"
    Try
        If Not System.IO.Directory.Exists(sLogFolder) Then System.IO.Directory.CreateDirectory(sLogFolder)
    Catch
    End Try
    Dim sLogFilePath As String = System.IO.Path.Combine(sLogFolder, "JC00_Repoint_" & DateTime.Now.ToString("yyyyMMdd_HHmmss") & ".txt")
    Try
        System.IO.File.WriteAllText(sLogFilePath, "JC00 Repoint To Library - " & DateTime.Now.ToString() & vbCrLf)
        System.IO.File.AppendAllText(sLogFilePath, "Top assembly: " & sTopAssemblyFullName & vbCrLf & vbCrLf)
    Catch
    End Try

    ' ---------- Step 1: walk assembly, find candidates, compute signatures ----------
    Dim oVisited As New HashSet(Of String)
    Dim oMatches As New List(Of JcMatch)
    Try
        WalkOccurrences(oAsmDoc.ComponentDefinition.Occurrences, oVisited, oMatches, _
            sLibraryFolder, sTokenPattern, bModeJC, bModeCC, sContentCenterFolder, oFastenerKeywords, _
            bModeJCCatalogue, oJCEntries, oJCMassBucket, _
            bModeCCCatalogue, oCCEntries, oCCMassBucket)
    Catch ex As Exception
        MessageBox.Show("Error while walking the assembly tree: " & ex.Message, "Error")
        Exit Sub
    End Try

    ' Internal duplicate scan
    Dim oInternalGroups As New List(Of InternalDupGroup)
    If bModeInternal Then
        Try
            oInternalGroups = FindInternalDuplicates(oAsmDoc)
        Catch ex As Exception
            MessageBox.Show("Error during internal duplicate scan: " & ex.Message, "Error")
        End Try
    End If

    If oMatches.Count = 0 AndAlso oInternalGroups.Count = 0 Then
        MessageBox.Show("No duplicates found - nothing to do.", "Nothing To Do")
        Exit Sub
    End If

    ' ---------- Compute candidate results for live-scan matches ----------
    For Each oM As JcMatch In oMatches
        If oM.oCandidateResults.Count > 0 Then Continue For  ' catalogue already pre-populated

        oM.oSourceSig = GetMassSignatureFromDocument(oM.oSourceDoc)
        oM.sSourcePartNumber = GetPropertyValue(oM.oSourceDoc, "Part Number")
        oM.sSourceDescription = GetPropertyValue(oM.oSourceDoc, "Description")
        oM.sSourceSpecification = GetPropertyValue(oM.oSourceDoc, "SPECIFICATION")

        For Each sCand As String In oM.oCandidates
            Dim oCR As New CandidateResult
            oCR.sPath = sCand
            Dim sCandExt As String = System.IO.Path.GetExtension(sCand).ToUpper()
            Dim sSourceType As String = If(oM.oSourceSig IsNot Nothing, oM.oSourceSig.sDocType, "")
            oCR.bTypeMatches = (sSourceType = "PART" AndAlso sCandExt = ".IPT") OrElse (sSourceType = "ASM" AndAlso sCandExt = ".IAM")
            If oCR.bTypeMatches AndAlso oM.oSourceSig IsNot Nothing Then
                GetCandidateInfoViaOpen(sCand, oCR)
                oCR.bIsIdentical = SignaturesMatch(oM.oSourceSig, oCR.oSig)
            End If
            oM.oCandidateResults.Add(oCR)
        Next
    Next

    ' ---------- Internal duplicate picker ----------
    If oInternalGroups.Count > 0 Then
        Dim oIntMap As Dictionary(Of String, String) = ShowInternalDupPickerForm(oInternalGroups)
        If oIntMap.Count > 0 Then
            Dim iIntDone As Integer = 0
            Dim sIntLog As String = "INTERNAL DUPLICATE REPOINTS:" & vbCrLf
            For Each oDoc As Document In ThisApplication.Documents
                Try
                    If oDoc.DocumentType <> kAssemblyDocumentObject Then Continue For
                    Dim bDocChanged As Boolean = False
                    For Each oOcc As ComponentOccurrence In oDoc.ComponentDefinition.Occurrences
                        Try
                            Dim sOccFull As String = oOcc.Definition.Document.FullFileName
                            If Not oIntMap.ContainsKey(sOccFull) Then Continue For
                            Dim sPrincipal As String = oIntMap(sOccFull)
                            Dim bRep As Boolean = False
                            Try : oOcc.Replace(sPrincipal, False) : bRep = True : Catch : End Try
                            If Not bRep Then
                                Try
                                    Dim oFD As FileDescriptor = oOcc.ReferencedFileDescriptor
                                    If oFD IsNot Nothing Then : oFD.ReplaceReference(sPrincipal) : bRep = True : End If
                                Catch : End Try
                            End If
                            If bRep Then
                                bDocChanged = True
                                iIntDone += 1
                                sIntLog &= System.IO.Path.GetFileName(sOccFull) & "  -->  " & System.IO.Path.GetFileName(sPrincipal) & vbCrLf
                            End If
                        Catch : End Try
                    Next
                    If bDocChanged Then Try : oDoc.Save2(False) : Catch : End Try
                Catch : End Try
            Next
            MessageBox.Show(sIntLog & vbCrLf & iIntDone & " occurrence(s) repointed.", "Internal Duplicates - Done")
        End If
    End If

    ' ---------- REPORT ONLY MODE ----------
    If bReportOnly Then
        Try
            WriteInvestigateDuplicatesReport(oAsmDoc, oMatches, oInternalGroups, sLogFilePath)
            Dim sReportPath As String = ""
            Try
                Dim sAsmName As String = System.IO.Path.GetFileNameWithoutExtension(oAsmDoc.FullFileName)
                Dim oProjMatch As System.Text.RegularExpressions.Match = System.Text.RegularExpressions.Regex.Match(sAsmName, "^[A-Z]{1,4}\d{3,6}")
                Dim sProjectPrefix As String = If(oProjMatch.Success, oProjMatch.Value.ToUpper(), "UNKNOWN")
                sReportPath = System.IO.Path.Combine(System.IO.Path.GetDirectoryName(sLogFilePath), sProjectPrefix & "_Investigate_Duplicates_" & DateTime.Now.ToString("yyyyMMdd_HHmmss") & ".txt")
            Catch
                sReportPath = System.IO.Path.ChangeExtension(sLogFilePath, "_Investigate_Duplicates.txt")
            End Try
            MessageBox.Show("Report-only mode complete." & vbCrLf & "Investigation report written and will open:" & vbCrLf & sReportPath, "Report Only")
            ' Open the report in the default text editor
            Try
                System.Diagnostics.Process.Start(sReportPath)
            Catch
                ' Fallback if Process.Start fails
                Try
                    System.Diagnostics.Process.Start("notepad.exe", sReportPath)
                Catch
                End Try
            End Try
        Catch exRep As Exception
            MessageBox.Show("Report generation failed: " & exRep.Message, "Report Error")
        End Try
        Exit Sub
    End If

    If oMatches.Count = 0 Then Exit Sub

    ' ---------- Filter picker: only parts with >= 1 confirmed identical match ----------
    Dim oMatchesWithHits As New List(Of JcMatch)
    Dim oOriginalIndexMap As New List(Of Integer)
    For iFilter As Integer = 0 To oMatches.Count - 1
        Dim bHasHit As Boolean = False
        For Each oCR As CandidateResult In oMatches(iFilter).oCandidateResults
            If oCR.bIsIdentical Then bHasHit = True : Exit For
        Next
        If bHasHit Then
            oMatchesWithHits.Add(oMatches(iFilter))
            oOriginalIndexMap.Add(iFilter)
        End If
    Next

    If oMatchesWithHits.Count = 0 Then
        MessageBox.Show("No parts found with a confirmed identical match in the library." & vbCrLf & _
            "Parts with no match are kept as project copies." & vbCrLf & vbCrLf & _
            "(" & oMatches.Count & " part(s) were checked.)", "No Matches Found")
        Exit Sub
    End If

    Dim oChoicesFiltered As Dictionary(Of Integer, String) = ShowRepointPickerForm(oMatchesWithHits)
    If oChoicesFiltered Is Nothing Then
        MessageBox.Show("Cancelled - no changes made.", "Cancelled")
        Exit Sub
    End If

    ' Re-map filtered indices back to original oMatches indices
    Dim oChoices As New Dictionary(Of Integer, String)
    For Each kvp As KeyValuePair(Of Integer, String) In oChoicesFiltered
        oChoices(oOriginalIndexMap(kvp.Key)) = kvp.Value
    Next

    ' ---------- Build replace map ----------
    Dim oReplaceMap As New Dictionary(Of String, String)
    Dim sPlan As String = ""
    For iM As Integer = 0 To oMatches.Count - 1
        If Not oChoices.ContainsKey(iM) Then Continue For
        Dim sChosenLib As String = oChoices(iM)
        If String.Compare(sChosenLib, sTopAssemblyFullName, True) = 0 Then
            sPlan &= vbCrLf & "SAFETY SKIP: chosen file matches top assembly - refusing. [" & oMatches(iM).sSourceFile & "]"
            Continue For
        End If
        oReplaceMap(oMatches(iM).sSourceFile.ToUpper()) = sChosenLib
        sPlan &= vbCrLf & System.IO.Path.GetFileName(oMatches(iM).sSourceFile) & "  -->  " & sChosenLib
    Next

    If oReplaceMap.Count = 0 Then
        MessageBox.Show("No repoints selected - nothing to do. No files were changed.", "Nothing To Do")
        Exit Sub
    End If

    Dim oConfirm As DialogResult = MessageBox.Show( _
        "About to repoint " & oReplaceMap.Count & " sub(s):" & vbCrLf & sPlan & vbCrLf & vbCrLf & _
        "This will modify occurrence references and save affected documents. Continue?", _
        "Confirm Repoint", MessageBoxButtons.YesNo, MessageBoxIcon.Warning)
    If oConfirm <> DialogResult.Yes Then
        MessageBox.Show("Cancelled - no changes made.", "Cancelled")
        Exit Sub
    End If

    ' ---------- Apply replacements ----------
    Dim oDirtyDocs As New HashSet(Of Document)
    Dim sApplyLog As String = ""
    Dim oSuccessfulPairs As New List(Of RepointRecord)
    Try
        System.IO.File.AppendAllText(sLogFilePath, "PLAN:" & sPlan & vbCrLf & vbCrLf & "APPLY LOG:" & vbCrLf)
    Catch
    End Try
    Try
        ApplyRepoints(oAsmDoc, oReplaceMap, oDirtyDocs, sApplyLog, oSuccessfulPairs, "")
    Catch ex As Exception
        sApplyLog &= vbCrLf & "Error during apply: " & ex.Message
    End Try
    Try
        System.IO.File.AppendAllText(sLogFilePath, sApplyLog)
    Catch
    End Try

    ' ---------- Save ----------
    ' IMPORTANT: never save documents that live inside the JC Library or Content Center
    ' folders - they are read-only library references and must not appear in the Vault
    ' check-in queue.  IsLibraryDoc() guards this for every save below.
    Dim iSavedCount As Integer = 0
    Dim iSaveFailCount As Integer = 0
    For Each oDirtyDoc As Document In oDirtyDocs
        Try
            If IsLibraryDoc(oDirtyDoc.FullFileName, sLibraryFolder, sContentCenterFolder) Then
                sApplyLog &= vbCrLf & "SKIPPED save (library file - read-only): " & oDirtyDoc.FullFileName
                Continue For
            End If
            oDirtyDoc.Update2(True)
            If oDirtyDoc.Dirty Then
                oDirtyDoc.Save2(False)
                iSavedCount += 1
            End If
        Catch ex As Exception
            iSaveFailCount += 1
            sApplyLog &= vbCrLf & "FAILED to save " & oDirtyDoc.FullFileName & ": " & ex.Message
        End Try
    Next
    Try
        If Not IsLibraryDoc(oAsmDoc.FullFileName, sLibraryFolder, sContentCenterFolder) Then
            oAsmDoc.Update2(True)
            InventorVb.DocumentUpdate()
            If oAsmDoc.Dirty Then oAsmDoc.Save2(False)
        End If
    Catch ex As Exception
        sApplyLog &= vbCrLf & "FAILED to update/save top assembly: " & ex.Message
    End Try

    ' ---------- History file ----------
    Dim sHistoryFilePath As String = ""
    If oSuccessfulPairs.Count > 0 Then
        Try
            Dim sAsmFolder As String = System.IO.Path.GetDirectoryName(sTopAssemblyFullName)
            sHistoryFilePath = System.IO.Path.Combine(sAsmFolder, "JC Part Originally Featured in Asm List.txt")
            If Not System.IO.File.Exists(sHistoryFilePath) Then
                System.IO.File.WriteAllText(sHistoryFilePath, _
                    "JC Part Originally Featured In This Assembly - Repoint History" & vbCrLf & _
                    "Read by Reverse_JC00_Repoint_To_Original.iLogicVb to undo a repoint." & vbCrLf & _
                    "Format: MAP|<Original>|<New>|<Timestamp>|<TopAsm>|<OccPath>" & vbCrLf & vbCrLf)
            End If
            Dim sAppend As String = ""
            For Each oRec As RepointRecord In oSuccessfulPairs
                sAppend &= "MAP|" & oRec.sOriginal & "|" & oRec.sNew & "|" & DateTime.Now.ToString("yyyy-MM-dd HH:mm:ss") & "|" & sTopAssemblyFullName & "|" & oRec.sPath & vbCrLf
            Next
            System.IO.File.AppendAllText(sHistoryFilePath, sAppend)
        Catch ex As Exception
            Try : System.IO.File.AppendAllText(sLogFilePath, vbCrLf & "FAILED to write history: " & ex.Message) : Catch : End Try
        End Try
    End If

    MessageBox.Show("Repoint complete." & vbCrLf & vbCrLf & _
        "Sub(s) repointed: " & oReplaceMap.Count & vbCrLf & _
        "Documents saved: " & iSavedCount & vbCrLf & _
        "Save failures: " & iSaveFailCount & vbCrLf & _
        If(sHistoryFilePath <> "", vbCrLf & "History: " & sHistoryFilePath & vbCrLf, "") & vbCrLf & _
        "Full detail: " & sLogFilePath & vbCrLf & vbCrLf & _
        "VAULT CHECK-IN REMINDER:" & vbCrLf & _
        "When you check in, Vault may list JC Library or Content Center files" & vbCrLf & _
        "in the check-in queue. UNCHECK any file whose path contains:" & vbCrLf & _
        "  - " & sLibraryFolder & vbCrLf & _
        "  - " & sContentCenterFolder & vbCrLf & _
        "Only check in your project files. Library files must never be checked in.", _
        "Repoint Complete")

End Sub

' Helper - just returns the path string for message boxes (avoids inline concat confusion)
Function sCatalogueFilePath(s As String) As String
    Return s
End Function

' Returns True if the file lives inside the JC Library or Content Center folder.
' Used to prevent the rule from saving library files, which would make Vault
' try to check them in to the wrong location.
Function IsLibraryDoc(sFullPath As String, sLibFolder As String, sCCFolder As String) As Boolean
    Dim sUp As String = sFullPath.ToUpper()
    If sLibFolder <> "" AndAlso sUp.StartsWith(sLibFolder.ToUpper()) Then Return True
    If sCCFolder  <> "" AndAlso sUp.StartsWith(sCCFolder.ToUpper())  Then Return True
    Return False
End Function


' =====================================================================
' DATA CLASSES
' =====================================================================
Public Class JcMatch
    Public sSourceFile As String
    Public sToken As String
    Public sMatchType As String = "JC"
    Public oSourceDoc As Document
    Public oSourceSig As MassSig
    Public sSourcePartNumber As String
    Public sSourceDescription As String
    Public sSourceSpecification As String
    Public oCandidates As New List(Of String)
    Public oCandidateResults As New List(Of CandidateResult)
End Class

Public Class CandidateResult
    Public sPath As String
    Public oSig As MassSig
    Public bTypeMatches As Boolean
    Public bIsIdentical As Boolean
    Public sPartNumber As String
    Public sDescription As String
    Public sSpecification As String
End Class

Public Class RepointRecord
    Public sOriginal As String
    Public sNew As String
    Public sPath As String
End Class

Public Class MassSig
    Public sDocType As String
    Public dMass As Double
    Public dVolume As Double
    Public dArea As Double
    Public dCX As Double
    Public dCY As Double
    Public dCZ As Double
End Class

Public Class CatalogueEntry
    Public sToken    As String
    Public sName     As String
    Public sFullPath As String
    Public dMass     As Double
    Public dArea     As Double
    Public dVolume   As Double
    Public dCOMx     As Double
    Public dCOMy     As Double
    Public dCOMz     As Double
    Public sDocType  As String
    Public bHasGeo   As Boolean
    Public sMaterial As String   ' iProperty "Material"      e.g. "Stainless Steel 316", "Galvanised Steel"
    Public sSpec     As String   ' iProperty "SPECIFICATION" e.g. "SS 316", "GAL"
End Class


' =====================================================================
' CATALOGUE BUILD + LOAD  (shared by JC and CC)
' =====================================================================

' Builds a geometry catalogue for a library folder and writes it to sCatalogueFile.
' bIncludeAsm = True for JC (has .iam too), False for CC (mainly .ipt)
Sub BuildCatalogue(sFolder As String, sCatalogueFile As String, bIncludeAsm As Boolean)
    Dim oAllFiles As New List(Of String)
    Try
        For Each sF As String In System.IO.Directory.GetFiles(sFolder, "*.ipt", System.IO.SearchOption.AllDirectories)
            If sF.ToUpper().Contains("\OLDVERSIONS\") Then Continue For
            If sF.ToUpper().Contains("\OLD VERSIONS\") Then Continue For
            oAllFiles.Add(sF)
        Next
        If bIncludeAsm Then
            For Each sF As String In System.IO.Directory.GetFiles(sFolder, "*.iam", System.IO.SearchOption.AllDirectories)
                If sF.ToUpper().Contains("\OLDVERSIONS\") Then Continue For
                If sF.ToUpper().Contains("\OLD VERSIONS\") Then Continue For
                oAllFiles.Add(sF)
            Next
        End If
    Catch ex As Exception
        MessageBox.Show("Error scanning folder: " & ex.Message, "Scan Error")
        Exit Sub
    End Try

    If oAllFiles.Count = 0 Then
        MessageBox.Show("No files found to catalogue in:" & vbCrLf & sFolder, "Nothing Found")
        Exit Sub
    End If

    Dim oLines As New List(Of String)
    oLines.Add("#CATALOGUE v1.0")
    oLines.Add("#Generated: " & DateTime.Now.ToString("yyyy-MM-dd HH:mm:ss"))
    oLines.Add("#Folder: " & sFolder)
    oLines.Add("#Columns: Token" & Chr(9) & "DisplayName" & Chr(9) & "FullPath" & Chr(9) & "MassKg" & Chr(9) & "SurfaceArea" & Chr(9) & "Volume" & Chr(9) & "COMx" & Chr(9) & "COMy" & Chr(9) & "COMz" & Chr(9) & "DocType" & Chr(9) & "Material" & Chr(9) & "Specification")

    Dim iDone As Integer = 0
    Dim iFailed As Integer = 0

    For Each sFilePath As String In oAllFiles
        Dim sName    As String = System.IO.Path.GetFileNameWithoutExtension(sFilePath)
        Dim sExt     As String = System.IO.Path.GetExtension(sFilePath).ToUpper()
        Dim sDocType As String = If(sExt = ".IPT", "PART", "ASM")

        Dim sToken As String = ""
        Dim oTokMatch As System.Text.RegularExpressions.Match = _
            System.Text.RegularExpressions.Regex.Match(sName, "JC00\d+", System.Text.RegularExpressions.RegexOptions.IgnoreCase)
        If oTokMatch.Success Then sToken = oTokMatch.Value.ToUpper()

        Dim oDoc As Document = Nothing
        Dim bWasOpen As Boolean = False
        Try
            For Each oOpenDoc As Document In ThisApplication.Documents
                If String.Compare(oOpenDoc.FullFileName, sFilePath, True) = 0 Then
                    oDoc = oOpenDoc : bWasOpen = True : Exit For
                End If
            Next
            If oDoc Is Nothing Then oDoc = ThisApplication.Documents.Open(sFilePath, False)
        Catch
            iFailed += 1
            oLines.Add(sToken & Chr(9) & sName & Chr(9) & sFilePath & Chr(9) & "" & Chr(9) & "" & Chr(9) & "" & Chr(9) & "" & Chr(9) & "" & Chr(9) & "" & Chr(9) & sDocType & Chr(9) & "" & Chr(9) & "")
            Continue For
        End Try

        Try
            Dim oMP As MassProperties = Nothing
            If oDoc.DocumentType = kPartDocumentObject Then
                Try : oMP = CType(oDoc, PartDocument).ComponentDefinition.MassProperties : Catch : End Try
            ElseIf oDoc.DocumentType = kAssemblyDocumentObject Then
                Try : oMP = CType(oDoc, AssemblyDocument).ComponentDefinition.MassProperties : Catch : End Try
            End If

            Dim sMass As String = "" : Dim sArea As String = "" : Dim sVol As String = ""
            Dim sCOMx As String = "" : Dim sCOMy As String = "" : Dim sCOMz As String = ""
            If oMP IsNot Nothing Then
                Try : sMass = oMP.Mass.ToString("F6") : Catch : End Try
                Try : sArea = oMP.Area.ToString("F4") : Catch : End Try
                Try : sVol  = oMP.Volume.ToString("F4") : Catch : End Try
                Try : sCOMx = oMP.CenterOfMass.X.ToString("F4") : Catch : End Try
                Try : sCOMy = oMP.CenterOfMass.Y.ToString("F4") : Catch : End Try
                Try : sCOMz = oMP.CenterOfMass.Z.ToString("F4") : Catch : End Try
            End If
            ' Read material and specification iProperties - critical for CC matching
            ' (SS 316 and GAL bolts are geometrically identical; spec distinguishes them)
            Dim sMat  As String = GetPropertyValue(oDoc, "Material")
            Dim sSpec As String = GetPropertyValue(oDoc, "SPECIFICATION")
            If sSpec = "" Then sSpec = GetPropertyValue(oDoc, "Specification")
            oLines.Add(sToken & Chr(9) & sName & Chr(9) & sFilePath & Chr(9) & sMass & Chr(9) & sArea & Chr(9) & sVol & Chr(9) & sCOMx & Chr(9) & sCOMy & Chr(9) & sCOMz & Chr(9) & sDocType & Chr(9) & sMat & Chr(9) & sSpec)
            iDone += 1
        Catch
            iFailed += 1
            oLines.Add(sToken & Chr(9) & sName & Chr(9) & sFilePath & Chr(9) & "" & Chr(9) & "" & Chr(9) & "" & Chr(9) & "" & Chr(9) & "" & Chr(9) & "" & Chr(9) & sDocType & Chr(9) & "" & Chr(9) & "")
        Finally
            If Not bWasOpen AndAlso oDoc IsNot Nothing Then
                Try
                    oDoc.Close(False)
                Catch
                End Try
            End If
        End Try
    Next

    Try
        System.IO.File.WriteAllLines(sCatalogueFile, oLines.ToArray())
    Catch ex As Exception
        MessageBox.Show("Failed to write catalogue:" & vbCrLf & sCatalogueFile & vbCrLf & ex.Message, "Write Error")
        Exit Sub
    End Try

    MessageBox.Show("Catalogue built." & vbCrLf & _
        "  Files catalogued: " & iDone & vbCrLf & _
        "  Failed (no geometry): " & iFailed & vbCrLf & _
        "  Output: " & sCatalogueFile & vbCrLf & vbCrLf & _
        "Check this file into Vault so the team can share it.", "Catalogue Built")
End Sub

Sub LoadCatalogue(sCatalogueFile As String, ByRef oEntries As List(Of CatalogueEntry), _
                  ByRef oBuckets As Dictionary(Of String, List(Of CatalogueEntry)))
    Try
        For Each sLine As String In System.IO.File.ReadAllLines(sCatalogueFile)
            If sLine.StartsWith("#") Then Continue For
            If Trim(sLine) = "" Then Continue For
            Dim oParts As String() = sLine.Split(Chr(9))
            If oParts.Length < 10 Then Continue For
            Dim oE As New CatalogueEntry
            oE.sToken    = oParts(0).Trim().ToUpper()
            oE.sName     = oParts(1).Trim()
            oE.sFullPath = oParts(2).Trim()
            oE.sDocType  = oParts(9).Trim().ToUpper()
            ' Columns 10 and 11 added in v2026-10-27c: Material and Specification
            ' (older catalogues without them will have blank strings - tolerated)
            oE.sMaterial = If(oParts.Length > 10, oParts(10).Trim(), "")
            oE.sSpec     = If(oParts.Length > 11, oParts(11).Trim(), "")
            Dim dM As Double = 0, dA As Double = 0, dV As Double = 0
            Dim dX As Double = 0, dY As Double = 0, dZ As Double = 0
            If Double.TryParse(oParts(3), dM) AndAlso Double.TryParse(oParts(4), dA) AndAlso Double.TryParse(oParts(5), dV) Then
                oE.dMass = dM : oE.dArea = dA : oE.dVolume = dV
                Double.TryParse(oParts(6), dX) : oE.dCOMx = dX
                Double.TryParse(oParts(7), dY) : oE.dCOMy = dY
                Double.TryParse(oParts(8), dZ) : oE.dCOMz = dZ
                oE.bHasGeo = True
            End If
            oEntries.Add(oE)
            Dim sBucket As String = dM.ToString("F3")
            If Not oBuckets.ContainsKey(sBucket) Then oBuckets(sBucket) = New List(Of CatalogueEntry)()
            oBuckets(sBucket).Add(oE)
        Next
    Catch
    End Try
End Sub

Function FindCatalogueCandidates(oSourceDoc As Document, sSourceFile As String, _
                                  oCatMassBucket As Dictionary(Of String, List(Of CatalogueEntry)), _
                                  oEntries As List(Of CatalogueEntry)) As List(Of CatalogueEntry)
    Dim oResults As New List(Of CatalogueEntry)
    Try
        Dim oSig As MassSig = GetMassSignatureFromDocument(oSourceDoc)
        If oSig Is Nothing Then Return oResults

        ' Read source doc material and spec for fingerprint comparison.
        ' For CC parts these distinguish SS 316 from GAL even when geometry is identical.
        Dim sSrcMaterial As String = GetPropertyValue(oSourceDoc, "Material").Trim().ToUpper()
        Dim sSrcSpec     As String = GetPropertyValue(oSourceDoc, "SPECIFICATION").Trim().ToUpper()
        If sSrcSpec = "" Then sSrcSpec = GetPropertyValue(oSourceDoc, "Specification").Trim().ToUpper()

        Dim oCandidates As New List(Of CatalogueEntry)
        For iBucket As Integer = -1 To 1
            Dim sBk As String = (oSig.dMass + iBucket * 0.001).ToString("F3")
            If oCatMassBucket.ContainsKey(sBk) Then oCandidates.AddRange(oCatMassBucket(sBk))
        Next
        For Each oE As CatalogueEntry In oCandidates
            If Not oE.bHasGeo Then Continue For
            If String.Compare(oE.sFullPath, sSourceFile, True) = 0 Then Continue For
            If oE.sDocType <> oSig.sDocType Then Continue For
            If Not RelClose(oSig.dMass,   oE.dMass)   Then Continue For
            If Not RelClose(oSig.dVolume, oE.dVolume) Then Continue For
            If Not RelClose(oSig.dArea,   oE.dArea)   Then Continue For
            If Not AbsClose(oSig.dCX,     oE.dCOMx)   Then Continue For
            If Not AbsClose(oSig.dCY,     oE.dCOMy)   Then Continue For
            If Not AbsClose(oSig.dCZ,     oE.dCOMz)   Then Continue For

            ' Material / spec fingerprint check.
            ' Rule: if EITHER side has a value, they must match.
            ' If BOTH are blank we allow it (library entry has no spec data).
            Dim sEntryMat  As String = oE.sMaterial.Trim().ToUpper()
            Dim sEntrySpec As String = oE.sSpec.Trim().ToUpper()
            If (sSrcMaterial <> "" OrElse sEntryMat <> "") AndAlso sSrcMaterial <> sEntryMat Then Continue For
            If (sSrcSpec <> "" OrElse sEntrySpec <> "") AndAlso sSrcSpec <> sEntrySpec Then Continue For

            oResults.Add(oE)
        Next
    Catch
    End Try
    Return oResults
End Function


' =====================================================================
' ASSEMBLY WALK
' =====================================================================
Sub WalkOccurrences(oOccs As Object, oVisited As HashSet(Of String), oMatches As List(Of JcMatch), _
    sLibraryFolder As String, sTokenPattern As String, _
    bModeJC As Boolean, bModeCC As Boolean, _
    sContentCenterFolder As String, oFastenerKeywords As String(), _
    bModeJCCatalogue As Boolean, oJCEntries As List(Of CatalogueEntry), oJCMassBucket As Dictionary(Of String, List(Of CatalogueEntry)), _
    bModeCCCatalogue As Boolean, oCCEntries As List(Of CatalogueEntry), oCCMassBucket As Dictionary(Of String, List(Of CatalogueEntry)))

    For Each oOcc As ComponentOccurrence In oOccs
        If oOcc.Suppressed Then Continue For
        Dim oDoc As Document = Nothing
        Dim sFull As String = ""
        Try
            oDoc = oOcc.Definition.Document
            sFull = oDoc.FullFileName
        Catch
            Continue For
        End Try
        If Trim(sFull) = "" Then Continue For
        If sFull.Contains("*") Then Continue For

        Dim sKey As String = sFull.ToUpper()
        If Not oVisited.Contains(sKey) Then
            oVisited.Add(sKey)

            If Not IsInExcludedFolder(sFull) Then
                Dim sName As String = System.IO.Path.GetFileNameWithoutExtension(sFull)
                Dim sNameUpper As String = sName.ToUpper()
                Dim bIsJCCandidate As Boolean = sNameUpper.Contains("JC") OrElse sNameUpper.Contains("SJD")

                ' --- JC CATALOGUE FAST PATH (token + geometry from map, no file opens) ---
                If bModeJCCatalogue AndAlso bIsJCCandidate Then
                    Dim oTok As System.Text.RegularExpressions.Match = System.Text.RegularExpressions.Regex.Match(sName, "JC00\d+", System.Text.RegularExpressions.RegexOptions.IgnoreCase)
                    Dim sToken As String = If(oTok.Success, oTok.Value.ToUpper(), "")
                    Dim oHits As New List(Of CatalogueEntry)
                    ' 1. Token matches from the catalogue (primary list)
                    If sToken <> "" Then
                        For Each oE As CatalogueEntry In oJCEntries
                            If oE.sToken = sToken AndAlso String.Compare(oE.sFullPath, sFull, True) <> 0 Then
                                oHits.Add(oE)
                            End If
                        Next
                    End If
                    ' 2. Geometry confirmation from catalogue (adds any extra geometry matches)
                    Dim oGeoHits As List(Of CatalogueEntry) = FindCatalogueCandidates(oDoc, sFull, oJCMassBucket, oJCEntries)
                    For Each oE As CatalogueEntry In oGeoHits
                        Dim bAlready As Boolean = False
                        For Each oExisting As CatalogueEntry In oHits
                            If String.Compare(oExisting.sFullPath, oE.sFullPath, True) = 0 Then bAlready = True : Exit For
                        Next
                        If Not bAlready Then oHits.Add(oE)
                    Next
                    If oHits.Count > 0 Then
                        Dim oM As New JcMatch
                        oM.sSourceFile = sFull : oM.oSourceDoc = oDoc : oM.sMatchType = "JC"
                        oM.sToken = If(sToken <> "", sToken, sName)
                        For Each oHit As CatalogueEntry In oHits
                            oM.oCandidates.Add(oHit.sFullPath)
                            Dim oCR As New CandidateResult
                            oCR.sPath = oHit.sFullPath : oCR.bTypeMatches = True
                            ' Mark identical only if geometry also matches (or if we have no geo data)
                            oCR.bIsIdentical = (Not oHit.bHasGeo) OrElse (oGeoHits.Exists(Function(x) String.Compare(x.sFullPath, oHit.sFullPath, True) = 0))
                            oCR.sPartNumber = "" : oCR.sDescription = oHit.sName : oCR.sSpecification = oHit.sSpec
                            oM.oCandidateResults.Add(oCR)
                        Next
                        oMatches.Add(oM)
                        GoTo NextOccurrence
                    End If
                End If

                ' --- CC CATALOGUE FAST PATH ---
                ' Skip parts that already live in the Content Center folder -
                ' we only want to catch local project copies, never CC-vs-CC matches.
                If bModeCCCatalogue AndAlso Not IsLibraryDoc(sFull, "", sContentCenterFolder) Then
                    Dim oCCHits As List(Of CatalogueEntry) = FindCatalogueCandidates(oDoc, sFull, oCCMassBucket, oCCEntries)
                    If oCCHits.Count > 0 Then
                        Dim oM As New JcMatch
                        oM.sSourceFile = sFull : oM.oSourceDoc = oDoc : oM.sMatchType = "CC" : oM.sToken = sName
                        For Each oHit As CatalogueEntry In oCCHits
                            oM.oCandidates.Add(oHit.sFullPath)
                            Dim oCR As New CandidateResult
                            oCR.sPath = oHit.sFullPath : oCR.bTypeMatches = True : oCR.bIsIdentical = True
                            oCR.sPartNumber = "" : oCR.sDescription = oHit.sName : oCR.sSpecification = oHit.sSpec
                            oM.oCandidateResults.Add(oCR)
                        Next
                        oMatches.Add(oM)
                        GoTo NextOccurrence
                    End If
                End If

                ' --- JC LIVE SCAN ---
                If bModeJC AndAlso bIsJCCandidate Then
                    Dim sToken As String = ""
                    Dim oCandidates As New List(Of String)
                    Dim oRegexMatch As System.Text.RegularExpressions.Match = System.Text.RegularExpressions.Regex.Match(sName, "JC00\d+", System.Text.RegularExpressions.RegexOptions.IgnoreCase)
                    If oRegexMatch.Success Then
                        sToken = oRegexMatch.Value.ToUpper()
                        oCandidates = FindLibraryCandidates(sLibraryFolder, sToken, sFull)
                    End If
                    If oCandidates.Count = 0 Then oCandidates = FindAllLibraryCandidates(sLibraryFolder, sFull)
                    If oCandidates.Count > 0 Then
                        Dim oM As New JcMatch
                        oM.sSourceFile = sFull : oM.sToken = If(sToken <> "", sToken, sName)
                        oM.oSourceDoc = oDoc : oM.oCandidates = oCandidates : oM.sMatchType = "JC"
                        oMatches.Add(oM)
                    End If
                End If

                ' --- CC LIVE SCAN ---
                If bModeCC Then
                    Dim bIsFastener As Boolean = False
                    For Each sKw As String In oFastenerKeywords
                        If sNameUpper.Contains(sKw.ToUpper()) Then bIsFastener = True : Exit For
                    Next
                    If bIsFastener Then
                        Dim oCCCands As List(Of String) = FindContentCenterCandidates(sContentCenterFolder, sName, sFull)
                        If oCCCands.Count > 0 Then
                            Dim oM As New JcMatch
                            oM.sSourceFile = sFull : oM.sToken = sName
                            oM.oSourceDoc = oDoc : oM.oCandidates = oCCCands : oM.sMatchType = "CC"
                            oMatches.Add(oM)
                        End If
                    End If
                End If
            End If

            Try
                WalkOccurrences(oOcc.SubOccurrences, oVisited, oMatches, _
                    sLibraryFolder, sTokenPattern, bModeJC, bModeCC, sContentCenterFolder, oFastenerKeywords, _
                    bModeJCCatalogue, oJCEntries, oJCMassBucket, _
                    bModeCCCatalogue, oCCEntries, oCCMassBucket)
            Catch
            End Try
        End If
        NextOccurrence:
    Next
End Sub

Function FindLibraryCandidates(sLibraryFolder As String, sToken As String, sExclude As String) As List(Of String)
    Dim oResults As New List(Of String)
    Try
        For Each sF As String In System.IO.Directory.GetFiles(sLibraryFolder, "*" & sToken & "*.ipt", System.IO.SearchOption.AllDirectories)
            If sF.ToUpper().Contains("\OLDVERSIONS\") OrElse sF.ToUpper().Contains("\OLD VERSIONS\") Then Continue For
            If String.Compare(sF, sExclude, True) <> 0 Then oResults.Add(sF)
        Next
        For Each sF As String In System.IO.Directory.GetFiles(sLibraryFolder, "*" & sToken & "*.iam", System.IO.SearchOption.AllDirectories)
            If sF.ToUpper().Contains("\OLDVERSIONS\") OrElse sF.ToUpper().Contains("\OLD VERSIONS\") Then Continue For
            If String.Compare(sF, sExclude, True) <> 0 Then oResults.Add(sF)
        Next
    Catch
    End Try
    Return oResults
End Function

Function FindAllLibraryCandidates(sLibraryFolder As String, sExclude As String) As List(Of String)
    Dim oResults As New List(Of String)
    Try
        For Each sF As String In System.IO.Directory.GetFiles(sLibraryFolder, "*.ipt", System.IO.SearchOption.AllDirectories)
            If sF.ToUpper().Contains("\OLDVERSIONS\") OrElse sF.ToUpper().Contains("\OLD VERSIONS\") Then Continue For
            If String.Compare(sF, sExclude, True) <> 0 Then oResults.Add(sF)
        Next
        For Each sF As String In System.IO.Directory.GetFiles(sLibraryFolder, "*.iam", System.IO.SearchOption.AllDirectories)
            If sF.ToUpper().Contains("\OLDVERSIONS\") OrElse sF.ToUpper().Contains("\OLD VERSIONS\") Then Continue For
            If String.Compare(sF, sExclude, True) <> 0 Then oResults.Add(sF)
        Next
    Catch
    End Try
    Return oResults
End Function

Function FindContentCenterCandidates(sCCFolder As String, sSourceName As String, sExclude As String) As List(Of String)
    Dim oResults As New List(Of String)
    Try
        For Each sF As String In System.IO.Directory.GetFiles(sCCFolder, "*" & sSourceName & "*", System.IO.SearchOption.AllDirectories)
            If sF.ToUpper().Contains("\OLDVERSIONS\") OrElse sF.ToUpper().Contains("\OLD VERSIONS\") Then Continue For
            Dim sExt As String = System.IO.Path.GetExtension(sF).ToUpper()
            If sExt <> ".IPT" AndAlso sExt <> ".IAM" Then Continue For
            If String.Compare(sF, sExclude, True) <> 0 Then oResults.Add(sF)
        Next
    Catch
    End Try
    Return oResults
End Function


' =====================================================================
' INTERNAL DUPLICATES
' =====================================================================
Public Class InternalDupGroup
    Public oFiles As New List(Of String)
    Public oFileDocs As New List(Of Document)
    Public sSigKey As String = ""
End Class

Function FindInternalDuplicates(oAsmDoc As AssemblyDocument) As List(Of InternalDupGroup)
    Dim oSigMap As New Dictionary(Of String, List(Of Tuple(Of String, Document)))(StringComparer.OrdinalIgnoreCase)
    Dim oVisited As New HashSet(Of String)(StringComparer.OrdinalIgnoreCase)
    For Each oDoc As Document In oAsmDoc.AllReferencedDocuments
        Try
            If oDoc.DocumentType <> kPartDocumentObject Then Continue For
            Dim sFull As String = oDoc.FullFileName
            If Trim(sFull) = "" OrElse sFull.Contains("*") Then Continue For
            If IsInExcludedFolder(sFull) Then Continue For
            If oVisited.Contains(sFull.ToUpper()) Then Continue For
            oVisited.Add(sFull.ToUpper())
            Dim sNameFG As String = System.IO.Path.GetFileNameWithoutExtension(sFull).ToUpper()
            If System.Text.RegularExpressions.Regex.IsMatch(sNameFG, "[0-9]+X[0-9]", System.Text.RegularExpressions.RegexOptions.IgnoreCase) Then Continue For
            If IsFrameGeneratorMember(oDoc) Then Continue For
            Dim oSig As MassSig = GetMassSignatureFromDocument(oDoc)
            If oSig Is Nothing Then Continue For
            Dim sSigKey As String = FormatSig(oSig)
            If Not oSigMap.ContainsKey(sSigKey) Then oSigMap(sSigKey) = New List(Of Tuple(Of String, Document))()
            oSigMap(sSigKey).Add(Tuple.Create(sFull, oDoc))
        Catch
        End Try
    Next
    Dim oGroups As New List(Of InternalDupGroup)
    For Each kvp As KeyValuePair(Of String, List(Of Tuple(Of String, Document))) In oSigMap
        If kvp.Value.Count < 2 Then Continue For
        Dim oNames As New HashSet(Of String)(StringComparer.OrdinalIgnoreCase)
        For Each t As Tuple(Of String, Document) In kvp.Value
            oNames.Add(System.IO.Path.GetFileName(t.Item1).ToUpper())
        Next
        If oNames.Count < 2 Then Continue For
        Dim oGrp As New InternalDupGroup : oGrp.sSigKey = kvp.Key
        For Each t As Tuple(Of String, Document) In kvp.Value
            oGrp.oFiles.Add(t.Item1) : oGrp.oFileDocs.Add(t.Item2)
        Next
        oGroups.Add(oGrp)
    Next
    Return oGroups
End Function

Function ShowInternalDupPickerForm(oGroups As List(Of InternalDupGroup)) As Dictionary(Of String, String)
    Dim oResult As New Dictionary(Of String, String)(StringComparer.OrdinalIgnoreCase)
    Dim oForm As New Form()
    oForm.Text = "Internal Duplicates - Pick Principal For Each Group"
    oForm.StartPosition = FormStartPosition.CenterScreen
    oForm.TopMost = True : oForm.Width = 620
    oForm.Height = Math.Min(700, 120 + oGroups.Count * 140)
    oForm.FormBorderStyle = FormBorderStyle.FixedDialog
    oForm.AutoScroll = True
    Dim oPanel As New Panel() : oPanel.AutoScroll = True : oPanel.Dock = DockStyle.Fill
    oForm.Controls.Add(oPanel)
    Dim iY As Integer = 10
    Dim oGroupRadios As New List(Of List(Of RadioButton))()
    For Each oGrp As InternalDupGroup In oGroups
        Dim oLbl As New Label()
        oLbl.Text = "Identical geometry " & oGrp.sSigKey & " - pick principal:"
        oLbl.Left = 10 : oLbl.Top = iY : oLbl.Width = 580 : oLbl.AutoSize = True
        oPanel.Controls.Add(oLbl) : iY += 22
        Dim oRadios As New List(Of RadioButton)()
        For i As Integer = 0 To oGrp.oFiles.Count - 1
            Dim oRad As New RadioButton()
            oRad.Text = System.IO.Path.GetFileName(oGrp.oFiles(i))
            oRad.Tag = oGrp.oFiles(i) : oRad.Left = 25 : oRad.Top = iY : oRad.Width = 560
            oRad.Checked = (i = 0)
            oPanel.Controls.Add(oRad) : oRadios.Add(oRad) : iY += 22
        Next
        oGroupRadios.Add(oRadios) : iY += 10
    Next
    Dim oOk As New Button() : oOk.Text = "Repoint" : oOk.Left = 410 : oOk.Top = iY + 5 : oOk.Width = 90
    oOk.DialogResult = DialogResult.OK : oPanel.Controls.Add(oOk) : oForm.AcceptButton = oOk
    Dim oSkip As New Button() : oSkip.Text = "Skip All" : oSkip.Left = 510 : oSkip.Top = iY + 5 : oSkip.Width = 90
    oSkip.DialogResult = DialogResult.Cancel : oPanel.Controls.Add(oSkip) : oForm.CancelButton = oSkip
    If oForm.ShowDialog() <> DialogResult.OK Then Return oResult
    For i As Integer = 0 To oGroups.Count - 1
        Dim sPrincipal As String = ""
        For Each oRad As RadioButton In oGroupRadios(i)
            If oRad.Checked Then sPrincipal = CStr(oRad.Tag) : Exit For
        Next
        If sPrincipal = "" Then Continue For
        For Each sFile As String In oGroups(i).oFiles
            If String.Compare(sFile, sPrincipal, True) <> 0 Then oResult(sFile) = sPrincipal
        Next
    Next
    Return oResult
End Function

Function IsFrameGeneratorMember(oDoc As Document) As Boolean
    Try
        For Each oParentDesc As DocumentDescriptor In oDoc.ReferencingDocuments
            Try
                Dim oParent As Document = oParentDesc.ReferencedDocument
                If oParent Is Nothing OrElse oParent.DocumentType <> kAssemblyDocumentObject Then Continue For
                Dim sPN As String = System.IO.Path.GetFileNameWithoutExtension(oParent.FullFileName).ToUpper()
                If sPN.EndsWith("-F") OrElse sPN.EndsWith("_F") OrElse sPN.Contains("-F_") OrElse sPN.Contains("_F_") OrElse sPN.Contains("FRAME") Then Return True
            Catch
            End Try
        Next
    Catch
    End Try
    Return False
End Function


' =====================================================================
' MODE SELECTION FORM
' =====================================================================
Sub ShowModeSelectionForm(ByRef bModeJC As Boolean, ByRef bModeCC As Boolean, ByRef bModeInternal As Boolean, _
                          ByRef bModeJCCatalogue As Boolean, ByRef bModeCCCatalogue As Boolean, ByRef bReportOnly As Boolean)
    Dim oForm As New Form()
    oForm.Text = "Duplicate Check - Select Mode"
    oForm.StartPosition = FormStartPosition.CenterScreen
    oForm.TopMost = True : oForm.Width = 540 : oForm.Height = 500
    oForm.FormBorderStyle = FormBorderStyle.FixedDialog
    oForm.MaximizeBox = False : oForm.MinimizeBox = False

    Dim oLbl As New Label()
    oLbl.Text = "Select which duplicate check(s) to run:"
    oLbl.Left = 15 : oLbl.Top = 15 : oLbl.Width = 480 : oLbl.Height = 20
    oForm.Controls.Add(oLbl)

    Dim oChkJCCat As New CheckBox()
    oChkJCCat.Text = "JC Catalogue (FAST) - geometry match via catalogue, zero file opens"
    oChkJCCat.Left = 15 : oChkJCCat.Top = 45 : oChkJCCat.Width = 480 : oChkJCCat.Height = 20 : oChkJCCat.Checked = True
    oForm.Controls.Add(oChkJCCat)

    Dim oChkCCCat As New CheckBox()
    oChkCCCat.Text = "CC Catalogue (FAST) - geometry match vs Content Center catalogue"
    oChkCCCat.Left = 15 : oChkCCCat.Top = 70 : oChkCCCat.Width = 480 : oChkCCCat.Height = 20 : oChkCCCat.Checked = True
    oForm.Controls.Add(oChkCCCat)

    Dim oChkJC As New CheckBox()
    oChkJC.Text = "JC Library (LIVE SCAN) - opens every library file (slow)"
    oChkJC.Left = 15 : oChkJC.Top = 100 : oChkJC.Width = 480 : oChkJC.Height = 20 : oChkJC.Checked = False
    oForm.Controls.Add(oChkJC)

    Dim oChkCC As New CheckBox()
    oChkCC.Text = "Content Center (LIVE SCAN) - keyword-based fastener search (slow)"
    oChkCC.Left = 15 : oChkCC.Top = 125 : oChkCC.Width = 480 : oChkCC.Height = 20 : oChkCC.Checked = False
    oForm.Controls.Add(oChkCC)

    Dim oChkInt As New CheckBox()
    oChkInt.Text = "Internal - find geometry duplicates within this assembly"
    oChkInt.Left = 15 : oChkInt.Top = 150 : oChkInt.Width = 480 : oChkInt.Height = 20 : oChkInt.Checked = False
    oForm.Controls.Add(oChkInt)

    Dim oChkReport As New CheckBox()
    oChkReport.Text = "Report Only (no changes - write investigation text file)"
    oChkReport.Left = 15 : oChkReport.Top = 180 : oChkReport.Width = 480 : oChkReport.Height = 22 : oChkReport.Checked = True
    oForm.Controls.Add(oChkReport)

    Dim oNote As New Label()
    oNote.Text = "Catalogue modes: if no catalogue file exists you will be prompted to build" & vbCrLf & _
        "it (Inventor opens each library file once, then saves a .txt in the library" & vbCrLf & _
        "root). Check that .txt into Vault so the whole team shares it." & vbCrLf & vbCrLf & _
        "Picker only shows parts with a confirmed identical match - parts with no" & vbCrLf & _
        "match are silently kept as project copies."
    oNote.Left = 15 : oNote.Top = 215 : oNote.Width = 480 : oNote.Height = 100
    oForm.Controls.Add(oNote)

    Dim oOk As New Button()
    oOk.Text = "OK" : oOk.Left = 310 : oOk.Top = 430 : oOk.Width = 80
    oOk.DialogResult = DialogResult.OK
    oForm.Controls.Add(oOk) : oForm.AcceptButton = oOk

    Dim oCancel As New Button()
    oCancel.Text = "Cancel" : oCancel.Left = 400 : oCancel.Top = 430 : oCancel.Width = 80
    oCancel.DialogResult = DialogResult.Cancel
    oForm.Controls.Add(oCancel) : oForm.CancelButton = oCancel

    If oForm.ShowDialog() = DialogResult.OK Then
        bModeJCCatalogue = oChkJCCat.Checked
        bModeCCCatalogue = oChkCCCat.Checked
        bModeJC          = oChkJC.Checked
        bModeCC          = oChkCC.Checked
        bModeInternal    = oChkInt.Checked
        bReportOnly      = oChkReport.Checked
    End If
End Sub


' =====================================================================
' UTILITY / GEOMETRY
' =====================================================================
Function IsInExcludedFolder(sFullFileName As String) As Boolean
    Dim sU As String = sFullFileName.ToUpper()
    If sU.Contains("VAULT\PROJECTS\JAMESON CELL\SJD00-GT STANDARD") Then Return True
    If sU.Contains("C:\VAULT\LIBRARIES\JC LIBRARY") Then Return True
    If sU.Contains("VAULT\CONTENT CENTER FILES") Then Return True
    Return False
End Function

Function GetMassSignatureFromDocument(oDoc As Document) As MassSig
    Try
        Dim oMP As MassProperties = Nothing
        Dim sType As String = ""
        If oDoc.DocumentType = kPartDocumentObject Then
            oMP = CType(oDoc, PartDocument).ComponentDefinition.MassProperties : sType = "PART"
        ElseIf oDoc.DocumentType = kAssemblyDocumentObject Then
            oMP = CType(oDoc, AssemblyDocument).ComponentDefinition.MassProperties : sType = "ASM"
        Else
            Return Nothing
        End If
        Return BuildSig(sType, oMP)
    Catch
        Return Nothing
    End Try
End Function

Sub GetCandidateInfoViaOpen(sFilePath As String, ByRef oCR As CandidateResult)
    Dim oCandDoc As Document = Nothing
    Dim bWeOpened As Boolean = False
    Try
        Try
            oCandDoc = ThisApplication.Documents.ItemByName(sFilePath)
        Catch
            oCandDoc = Nothing
        End Try
        If oCandDoc Is Nothing Then
            oCandDoc = ThisApplication.Documents.Open(sFilePath, False)
            bWeOpened = True
        End If
        Dim oMP As MassProperties = Nothing
        Dim sType As String = ""
        If oCandDoc.DocumentType = kPartDocumentObject Then
            oMP = CType(oCandDoc, PartDocument).ComponentDefinition.MassProperties : sType = "PART"
        ElseIf oCandDoc.DocumentType = kAssemblyDocumentObject Then
            oMP = CType(oCandDoc, AssemblyDocument).ComponentDefinition.MassProperties : sType = "ASM"
        Else
            Exit Sub
        End If
        oCR.oSig = BuildSig(sType, oMP)
        oCR.sPartNumber = GetPropertyValue(oCandDoc, "Part Number")
        oCR.sDescription = GetPropertyValue(oCandDoc, "Description")
        oCR.sSpecification = GetPropertyValue(oCandDoc, "SPECIFICATION")
    Catch
    Finally
        If bWeOpened AndAlso oCandDoc IsNot Nothing Then
            Try
                oCandDoc.Close(True)
            Catch
            End Try
        End If
    End Try
End Sub

Function GetPropertyValue(oDoc As Document, sPropName As String) As String
    Try
        For Each oSet As Inventor.PropertySet In oDoc.PropertySets
            Try
                Dim oProp As Inventor.Property = oSet.Item(sPropName)
                If oProp IsNot Nothing Then
                    Dim oVal As Object = oProp.Value
                    If oVal Is Nothing Then Return ""
                    Return oVal.ToString()
                End If
            Catch
            End Try
        Next
    Catch
    End Try
    Return ""
End Function

Function BuildSig(sType As String, oMP As MassProperties) As MassSig
    Dim oSig As New MassSig
    oSig.sDocType = sType : oSig.dMass = oMP.Mass : oSig.dVolume = oMP.Volume : oSig.dArea = oMP.Area
    Dim oCog As Point = oMP.CenterOfMass
    oSig.dCX = oCog.X : oSig.dCY = oCog.Y : oSig.dCZ = oCog.Z
    Return oSig
End Function

Function SignaturesMatch(a As MassSig, b As MassSig) As Boolean
    If a Is Nothing OrElse b Is Nothing Then Return False
    If a.sDocType <> b.sDocType Then Return False
    If Not RelClose(a.dMass, b.dMass) Then Return False
    If Not RelClose(a.dVolume, b.dVolume) Then Return False
    If Not RelClose(a.dArea, b.dArea) Then Return False
    If Not AbsClose(a.dCX, b.dCX) Then Return False
    If Not AbsClose(a.dCY, b.dCY) Then Return False
    If Not AbsClose(a.dCZ, b.dCZ) Then Return False
    Return True
End Function

Function RelClose(x As Double, y As Double) As Boolean
    Dim dDenom As Double = Math.Max(Math.Abs(x), Math.Abs(y))
    If dDenom < 0.0000001 Then Return True
    Return (Math.Abs(x - y) / dDenom) <= 0.001
End Function

Function AbsClose(x As Double, y As Double) As Boolean
    Return Math.Abs(x - y) <= 0.01
End Function

Function FormatSig(oSig As MassSig) As String
    If oSig Is Nothing Then Return "(no signature)"
    Return "Mass=" & oSig.dMass.ToString("F6") & " Vol=" & oSig.dVolume.ToString("F6") & _
           " Area=" & oSig.dArea.ToString("F6") & " CoM=(" & oSig.dCX.ToString("F4") & _
           "," & oSig.dCY.ToString("F4") & "," & oSig.dCZ.ToString("F4") & ")"
End Function

Function AddPropertyDiffLines(oGroupBox As GroupBox, iY As Integer, sFieldName As String, sSourceVal As String, sLibVal As String) As Integer
    Dim sMarker As String = If(String.Compare(Trim(sSourceVal), Trim(sLibVal), True) = 0, "(same)", "(DIFFERS)")
    Dim oLabel As New Label()
    oLabel.Text = "      " & sFieldName & " " & sMarker & ":   Source = '" & sSourceVal & "'     Library = '" & sLibVal & "'"
    oLabel.AutoSize = False : oLabel.Left = 30 : oLabel.Top = iY : oLabel.Width = 750 : oLabel.Height = 18 : oLabel.AutoEllipsis = True
    oGroupBox.Controls.Add(oLabel)
    Return 20
End Function


' =====================================================================
' APPLY REPOINTS
' =====================================================================
Sub ApplyRepoints(oDoc As Document, oReplaceMap As Dictionary(Of String, String), _
                  ByRef oDirtyDocs As HashSet(Of Document), ByRef sLog As String, _
                  ByRef oSuccessfulPairs As List(Of RepointRecord), sPathPrefix As String)
    If oDoc.DocumentType <> kAssemblyDocumentObject Then Exit Sub
    Dim oThisAsm As AssemblyDocument = oDoc
    Dim iIndex As Integer = 0
    For Each oOcc As ComponentOccurrence In oThisAsm.ComponentDefinition.Occurrences
        iIndex += 1
        Dim sThisPath As String = If(sPathPrefix = "", iIndex.ToString(), sPathPrefix & "." & iIndex.ToString())
        If oOcc.Suppressed Then Continue For
        Dim oChildDoc As Document = Nothing
        Dim sFull As String = ""
        Try
            oChildDoc = oOcc.Definition.Document : sFull = oChildDoc.FullFileName
        Catch
            Continue For
        End Try
        If Trim(sFull) = "" OrElse sFull.Contains("*") Then Continue For
        Dim sKey As String = sFull.ToUpper()
        If oReplaceMap.ContainsKey(sKey) Then
            Dim sNewFile As String = oReplaceMap(sKey)
            Try
                oOcc.Replace(sNewFile, False)
                oDirtyDocs.Add(oDoc)
                sLog &= vbCrLf & "REPOINTED in " & System.IO.Path.GetFileName(oDoc.FullFileName) & " [path " & sThisPath & "]: " & System.IO.Path.GetFileName(sFull) & "  -->  " & sNewFile
                Dim oRec As New RepointRecord : oRec.sOriginal = sFull : oRec.sNew = sNewFile : oRec.sPath = sThisPath
                oSuccessfulPairs.Add(oRec)
            Catch ex As Exception
                sLog &= vbCrLf & "FAILED to repoint " & System.IO.Path.GetFileName(sFull) & ": " & ex.Message
            End Try
            Continue For
        End If
        If IsInExcludedFolder(sFull) Then Continue For
        If oChildDoc.DocumentType = kAssemblyDocumentObject Then
            Try : ApplyRepoints(oChildDoc, oReplaceMap, oDirtyDocs, sLog, oSuccessfulPairs, sThisPath) : Catch : End Try
        End If
    Next
End Sub


' =====================================================================
' PICKER FORM
' =====================================================================
Function ShowRepointPickerForm(oMatches As List(Of JcMatch)) As Dictionary(Of Integer, String)
    Dim oForm As New Form()
    oForm.Text = "Duplicate Check - Keep Project Copy Or Repoint To Library"
    oForm.StartPosition = FormStartPosition.CenterScreen
    oForm.TopMost = True : oForm.MinimizeBox = False : oForm.MaximizeBox = False
    oForm.FormBorderStyle = FormBorderStyle.FixedDialog
    oForm.Width = 860 : oForm.Height = 660

    Dim oScrollPanel As New Panel()
    oScrollPanel.AutoScroll = True : oScrollPanel.Left = 10 : oScrollPanel.Top = 10
    oScrollPanel.Width = 820 : oScrollPanel.Height = 540
    oScrollPanel.BorderStyle = BorderStyle.FixedSingle
    oForm.Controls.Add(oScrollPanel)

    Dim iYPos As Integer = 10
    Dim oGroupRadios As New List(Of List(Of RadioButton))
    Dim oGroupTags   As New List(Of List(Of String))

    For iM As Integer = 0 To oMatches.Count - 1
        Dim oM As JcMatch = oMatches(iM)
        Dim iIdentCount As Integer = 0
        For Each oCR As CandidateResult In oM.oCandidateResults
            If oCR.bIsIdentical Then iIdentCount += 1
        Next
        Dim sStatus As String = If(iIdentCount = 1, "1 identical candidate", "AMBIGUOUS - " & iIdentCount & " identical candidates")
        Dim sTypeLabel As String = If(oM.sMatchType = "CC", "[CC] ", "[JC] ")

        Dim oGroupBox As New GroupBox()
        oGroupBox.Text = "Set " & (iM + 1) & " - " & sTypeLabel & System.IO.Path.GetFileName(oM.sSourceFile) & "   [" & sStatus & "]"
        oGroupBox.Left = 10 : oGroupBox.Top = iYPos : oGroupBox.Width = 780

        Dim iInnerY As Integer = 20
        Dim oRadiosGroup As New List(Of RadioButton)
        Dim oTagsGroup   As New List(Of String)

        Dim oKeepRadio As New RadioButton()
        oKeepRadio.Text = "KEEP project copy (no change) - " & oM.sSourceFile
        oKeepRadio.Left = 10 : oKeepRadio.Top = iInnerY : oKeepRadio.Width = 750
        oKeepRadio.AutoEllipsis = True : oKeepRadio.Checked = False
        oGroupBox.Controls.Add(oKeepRadio)
        oRadiosGroup.Add(oKeepRadio) : oTagsGroup.Add("") : iInnerY += 20

        For Each oCR As CandidateResult In oM.oCandidateResults
            If oCR.bIsIdentical Then
                Dim oRadio As New RadioButton()
                oRadio.Text = "POINT TO LIBRARY: " & oCR.sPath & "   (geometry confirmed identical)"
                oRadio.Left = 10 : oRadio.Top = iInnerY : oRadio.Width = 750
                oRadio.AutoEllipsis = True : oRadio.Checked = False
                oGroupBox.Controls.Add(oRadio)
                oRadiosGroup.Add(oRadio) : oTagsGroup.Add(oCR.sPath) : iInnerY += 20
                If oCR.sPartNumber <> "" OrElse oCR.sDescription <> "" OrElse oCR.sSpecification <> "" Then
                    iInnerY += AddPropertyDiffLines(oGroupBox, iInnerY, "Part Number", oM.sSourcePartNumber, oCR.sPartNumber)
                    iInnerY += AddPropertyDiffLines(oGroupBox, iInnerY, "Description", oM.sSourceDescription, oCR.sDescription)
                    iInnerY += AddPropertyDiffLines(oGroupBox, iInnerY, "Specification", oM.sSourceSpecification, oCR.sSpecification)
                    iInnerY += 6
                End If
            End If
        Next

        oGroupBox.Height = iInnerY + 15
        oScrollPanel.Controls.Add(oGroupBox)
        oGroupRadios.Add(oRadiosGroup) : oGroupTags.Add(oTagsGroup)
        iYPos += oGroupBox.Height + 10
    Next

    Dim oInstructionLabel As New Label()
    oInstructionLabel.Text = "Every set above must have an option selected before continuing."
    oInstructionLabel.Left = 10 : oInstructionLabel.Top = 558 : oInstructionLabel.Width = 500
    oForm.Controls.Add(oInstructionLabel)

    Dim oSelectAllLibBtn As New Button()
    oSelectAllLibBtn.Text = "Select All → Library"
    oSelectAllLibBtn.Left = 10 : oSelectAllLibBtn.Top = 580 : oSelectAllLibBtn.Width = 160
    oForm.Controls.Add(oSelectAllLibBtn)

    Dim oSelectAllKeepBtn As New Button()
    oSelectAllKeepBtn.Text = "Select All → Keep"
    oSelectAllKeepBtn.Left = 180 : oSelectAllKeepBtn.Top = 580 : oSelectAllKeepBtn.Width = 150
    oForm.Controls.Add(oSelectAllKeepBtn)

    Dim oOkButton As New Button()
    oOkButton.Text = "Apply Selections"
    oOkButton.Left = 590 : oOkButton.Top = 580 : oOkButton.Width = 130
    oForm.Controls.Add(oOkButton) : oForm.AcceptButton = oOkButton

    Dim oCancelButton As New Button()
    oCancelButton.Text = "Cancel"
    oCancelButton.Left = 730 : oCancelButton.Top = 580 : oCancelButton.Width = 100
    oForm.Controls.Add(oCancelButton) : oForm.CancelButton = oCancelButton

    Dim bCancelled As Boolean = False

    AddHandler oSelectAllLibBtn.Click, Sub(sender, e)
                                           For iG As Integer = 0 To oGroupRadios.Count - 1
                                               If oGroupRadios(iG).Count > 1 Then
                                                   For Each r As RadioButton In oGroupRadios(iG)
                                                       r.Checked = False
                                                   Next
                                                   oGroupRadios(iG)(1).Checked = True
                                               End If
                                           Next
                                       End Sub

    AddHandler oSelectAllKeepBtn.Click, Sub(sender, e)
                                            For iG As Integer = 0 To oGroupRadios.Count - 1
                                                For Each r As RadioButton In oGroupRadios(iG)
                                                    r.Checked = False
                                                Next
                                                If oGroupRadios(iG).Count > 0 Then oGroupRadios(iG)(0).Checked = True
                                            Next
                                        End Sub

    AddHandler oCancelButton.Click, Sub(sender, e)
                                         bCancelled = True : oForm.Close()
                                     End Sub

    AddHandler oOkButton.Click, Sub(sender, e)
                                    Dim oUnresolved As New List(Of Integer)
                                    For iG As Integer = 0 To oGroupRadios.Count - 1
                                        Dim bAny As Boolean = False
                                        For Each r As RadioButton In oGroupRadios(iG)
                                            If r.Checked Then bAny = True
                                        Next
                                        If Not bAny Then oUnresolved.Add(iG + 1)
                                    Next
                                    If oUnresolved.Count > 0 Then
                                        MessageBox.Show("Please select an option for Set(s): " & String.Join(", ", oUnresolved), "Selection Required")
                                    Else
                                        oForm.Close()
                                    End If
                                End Sub

    oForm.ShowDialog()
    If bCancelled Then Return Nothing

    Dim oResultMap As New Dictionary(Of Integer, String)
    For iG As Integer = 0 To oGroupRadios.Count - 1
        For iR As Integer = 0 To oGroupRadios(iG).Count - 1
            If oGroupRadios(iG)(iR).Checked Then
                Dim sTag As String = oGroupTags(iG)(iR)
                If sTag <> "" Then oResultMap(iG) = sTag
                Exit For
            End If
        Next
    Next
    Return oResultMap
End Function


' =====================================================================
' REPORT ONLY - hierarchical investigation text file
' Writes Drawing -> Model -> Sub hierarchy with candidate library matches.
' No files are modified.
' =====================================================================
Sub WriteInvestigateDuplicatesReport(oAsmDoc As AssemblyDocument, oMatches As List(Of JcMatch), _
                                     oInternalGroups As List(Of InternalDupGroup), sLogFilePath As String)
    ' Prefix report filename with project number extracted from top assembly name
    Dim sProjectPrefix As String = "UNKNOWN"
    Try
        Dim sAsmName As String = System.IO.Path.GetFileNameWithoutExtension(oAsmDoc.FullFileName)
        Dim oProjMatch As System.Text.RegularExpressions.Match = _
            System.Text.RegularExpressions.Regex.Match(sAsmName, "^[A-Z]{1,4}\d{3,6}")
        If oProjMatch.Success Then sProjectPrefix = oProjMatch.Value.ToUpper()
    Catch
    End Try
    Dim sReportFolder As String = System.IO.Path.GetDirectoryName(sLogFilePath)
    Dim sReportPath As String = System.IO.Path.Combine(sReportFolder, _
        sProjectPrefix & "_Investigate_Duplicates_" & DateTime.Now.ToString("yyyyMMdd_HHmmss") & ".txt")
    Dim sb As New System.Text.StringBuilder()

    ' Header with thick separators
    sb.AppendLine(New String("="c, 100))
    sb.AppendLine("INVESTIGATE DUPLICATES REPORT (report-only mode)")
    sb.AppendLine(New String("="c, 100))
    sb.AppendLine("Generated     : " & DateTime.Now.ToString())
    sb.AppendLine("Top assembly  : " & oAsmDoc.FullFileName)
    sb.AppendLine("Status        : No files were modified.")
    sb.AppendLine(New String("-"c, 100))
    sb.AppendLine("HIERARCHY (Drawing / Model / Sub -> items to investigate)")
    sb.AppendLine(New String("-"c, 100))
    sb.AppendLine()

    ' Simple hierarchy: group matches by parent path approximation
    ' For a full drawing walk we would need the drawings folder; this draft uses the assembly tree.
    Dim oByParent As New Dictionary(Of String, List(Of JcMatch))(StringComparer.OrdinalIgnoreCase)
    For Each oM As JcMatch In oMatches
        Dim sParent As String = "TOP"
        Try
            sParent = System.IO.Path.GetFileName(oM.oSourceDoc.FullFileName) ' placeholder grouping
        Catch
        End Try
        If Not oByParent.ContainsKey(sParent) Then oByParent(sParent) = New List(Of JcMatch)()
        oByParent(sParent).Add(oM)
    Next

    For Each kvp As KeyValuePair(Of String, List(Of JcMatch)) In oByParent
        sb.AppendLine(New String("="c, 80))
        sb.AppendLine("MODEL/SUB: " & kvp.Key)
        sb.AppendLine(New String("="c, 80))
        For Each oM As JcMatch In kvp.Value
            Dim iHits As Integer = 0
            For Each oCR As CandidateResult In oM.oCandidateResults
                If oCR.bIsIdentical Then iHits += 1
            Next
            If iHits = 0 Then Continue For
            sb.AppendLine()
            sb.AppendLine(">> ITEM TO INVESTIGATE: " & System.IO.Path.GetFileName(oM.sSourceFile))
            sb.AppendLine("   Current path : " & oM.sSourceFile)
            sb.AppendLine("   Type         : " & oM.sMatchType)
            sb.AppendLine("   Token        : " & oM.sToken)
            sb.AppendLine("   Candidates   : " & iHits & " confirmed identical")
            sb.AppendLine("   " & New String("-"c, 70))
            Dim bAnyPrinted As Boolean = False
            For Each oCR As CandidateResult In oM.oCandidateResults
                If oCR.bIsIdentical OrElse True Then
                    bAnyPrinted = True
                    Dim sGeoNote As String = If(oCR.bIsIdentical, "[geometry confirmed]", "[token match only]")
                    sb.AppendLine(">> ITEM TO COMPARE:    [LIB] " & oCR.sPath & "  " & sGeoNote)
                    Dim sSrcPN As String = If(oM.sSourcePartNumber, "")
                    Dim sSrcDesc As String = If(oM.sSourceDescription, "")
                    Dim sSrcSpec As String = If(oM.sSourceSpecification, "")
                    Dim sLibPN As String = If(oCR.sPartNumber, "")
                    Dim sLibDesc As String = If(oCR.sDescription, "")
                    Dim sLibSpec As String = If(oCR.sSpecification, "")
                    ' Always show the three property lines so the distinction is visible
                    Dim sMarkPN As String = If(String.Compare(Trim(sSrcPN), Trim(sLibPN), True) = 0, "(same)", "(DIFFERS)")
                    sb.AppendLine("   Part Number   " & sMarkPN & " : Source='" & sSrcPN & "'   Library='" & sLibPN & "'")
                    Dim sMarkDesc As String = If(String.Compare(Trim(sSrcDesc), Trim(sLibDesc), True) = 0, "(same)", "(DIFFERS)")
                    sb.AppendLine("   Description   " & sMarkDesc & " : Source='" & sSrcDesc & "'   Library='" & sLibDesc & "'")
                    Dim sMarkSpec As String = If(String.Compare(Trim(sSrcSpec), Trim(sLibSpec), True) = 0, "(same)", "(DIFFERS)")
                    sb.AppendLine("   Specification " & sMarkSpec & " : Source='" & sSrcSpec & "'   Library='" & sLibSpec & "'")
                    sb.AppendLine()
                End If
            Next
            If Not bAnyPrinted Then
                sb.AppendLine(">> ITEM TO COMPARE:    (no library path recorded for this hit)")
                sb.AppendLine()
            End If
            sb.AppendLine()
        Next
        sb.AppendLine()
    Next

    If oInternalGroups.Count > 0 Then
        sb.AppendLine(New String("="c, 100))
        sb.AppendLine("INTERNAL DUPLICATE GROUPS")
        sb.AppendLine(New String("="c, 100))
        For Each oGrp As InternalDupGroup In oInternalGroups
            sb.AppendLine()
            sb.AppendLine("  Group signature: " & oGrp.sSigKey)
            sb.AppendLine("  " & New String("-"c, 50))
            For Each sF As String In oGrp.oFiles
                sb.AppendLine("    - " & sF)
            Next
        Next
        sb.AppendLine()
    End If

    sb.AppendLine(New String("="c, 100))
    sb.AppendLine("END OF REPORT")
    sb.AppendLine(New String("="c, 100))

    Try
        System.IO.File.WriteAllText(sReportPath, sb.ToString())
    Catch ex As Exception
        Throw New Exception("Could not write report: " & ex.Message)
    End Try
End Sub
